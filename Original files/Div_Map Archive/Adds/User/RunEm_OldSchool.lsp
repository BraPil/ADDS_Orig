(if AppNam								; Code Version Indicator
	(princ (strcat "\n" AppNam " RunEmOld Loading."))
	(princ "\nCadet 2.0 RunEmOld Loading.")
)

(defun RunEmOld ( / F1 F2 F3 lstfile scrfile )		; Run Em, dang it!
	(if (= (getvar "ACADVER") "15.0")
		(if (not (member (strcase "DosLib2k.arx" T) (arx)))
			(if (findfile "doslib2k.arx")
				(arxload "doslib2k")
				(princ "\n*Buttons Error*: DosLIB Arx file not found on this system!")
			)
		)
		(if (not (member (strcase "DosLib14.arx" T) (arx)))
			(if (findfile "doslib14.arx")
				(arxload "doslib14")
				(princ "\n*Buttons Error*: DosLIB Arx file not found on this system!")
			)
		)
	)
	(if (findfile (strcat (getenv "TEMP") "\\TEMP.SCR"))
		(dos_delete (strcat (getenv "TEMP") "\\TEMP.SCR"))
	)
	(if (setq lstfile (open "FILES.LST" "r"))
		(progn
			(if (setq scrfile (open (strcat (getenv "TEMP") "\\TEMP.SCR") "w"))
				(progn
					(while (setq dwgname (read-line lstfile))
						(write-line (strcat "(if (> (getvar \"DBMOD\") 0) (command \".OPEN\" \"Y\" \"" dwgname "\") (command \".OPEN\" \"" dwgname "\"))") scrfile)
						(write-line "(command \"_.Zoom\" \"E\" \"_.Plot\" \"E\" \"0\")" scrfile)
					)
					(write-line "(if (> (getvar \"DBMOD\") 0) (progn (command \"_.QUIT\" \"_Y\")) (progn (command \"_.QUIT\")))" scrfile)
					(close scrfile)
				)
			)
			(close lstfile)
		)
	)
	(if (findfile (strcat (getenv "TEMP") "\\TEMP.SCR"))
		(command "SCRIPT" (strcat (getenv "TEMP") "\\TEMP.SCR"))
	)
	(princ)
)

(RunEmOld)								; Auto Run Statement (load-time run)
