;DEMO is an example of calling a self running command from pulldowns")
(defun C:DEMO()
	(print "/n DEMO is an example of calling a self running command from pulldowns")
)
;-------------------------------------------------------------------------------
(C:DEMO)
