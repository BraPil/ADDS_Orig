(if AppNam								; Code Version Indicator
	(princ (strcat "\n" AppNam " Fdr_Grey Loading."))
	(princ "\nAddsPlot Fdr_Grey Loading.")
)

(defun C:Fdr_Grey (  / 	fileptr notkeylst notkeystr keylen	; Grays all non-selected circuits
				laydef kvFROMlaydef keyFROMlaydef
				kv_lay kv_lay_make pos)
	(if cordkey
		(progn
			(if Bug (progn (princ "\nFdr_Grey - cordkey = ") (prin1 cordkey) (princ "\n")))
			(if (not LayChk)
				(load "Utils")
			)
			(if (not lst_vt_s)
				(progn
					(if (not bld_t_vlt) (load "TABLES"))
						(bld_t_vlt)
					)
			)
			(setq	notkeylst		(list )
					notkeystr		""
		 			keylen		(strlen (nth 0 cordkey))
					laydef		(tblnext "LAYER" T)
					pos			0
			)
			(while laydef
				(if (> (strlen (cdr (assoc 2 laydef))) 9)									;Checks to see if layer name lenght is greater than 9 characters
					(if (member (setq kvFROMlaydef (substr (cdr (assoc 2 laydef)) 9 2)) lst_vt_s)	;Checks to see if voltage part of layer name is in standard voltage list. If it is saves it.
						(progn
							(setq	keyFROMlaydef (substr (cdr (assoc 2 laydef)) 1 keylen))
						  	(if	(and	(not (member keyFROMlaydef cordkey))
									(not (member keyFROMlaydef notkeylst))
								)
								(setq	notkeylst		(cons keyFROMlaydef notkeylst)
										notkeystr		(strcat notkeystr keyFROMlaydef "*,")
								)
							)
							(if (= (substr (cdr (assoc 2 laydef)) 1 keylen) (nth 0 cordkey))
								(progn
									(setq kvlaydef (substr (cdr (assoc 2 laydef)) 9 2))
								)
							)
						)
					)
				)
				(setq laydef (tblnext "LAYER"))
			)
			(if (> (strlen notkeystr) 0)
				(progn
					(if Bug (princ (strcat "\nBug [" notkeystr "] Before")))
					(setq	notkeystr		(substr notkeystr 1 (1- (strlen notkeystr))))
					(if Bug (princ (strcat "\nBug [" notkeystr "] After")))
					(if (LayChk "????NO????")
						(command "_.LAYER" "C" "252" notkeystr "C" "3" "????NO????" "")
						(command "_.LAYER" "C" "252" notkeystr "")
					)
					(if (LayChk "????AA????")
						(command "_.LAYER" "C" "252" "????AA????" "")
					)
					(if (LayChk "????AB????")
						(command "_.LAYER" "C" "252" "????AB????" "")
					)
					(if (LayChk "????RD????")
						(command "_.LAYER" "C" "252" "????RD????" "")
					)
					(if (LayChk "????ST????")
						(command "_.LAYER" "C" "252" "????ST????" "")
					)
					(if (LayChk "????LM????")
						(command "_.LAYER" "C" "252" "????LM????" "")
					)	
				)
			)
			(if (not (member PlotType (list "DWF" "DWG" "DXF" "PDF")))
				(if (> (length CordKey) 1)
					(load (strcat _path-user "Custom50"))
					(if (/= (nth 0 CordKey) "")
						(load (strcat _path-user "Custom50"))
					)
				)
			)
		)
	)
	(princ)
)

(if (= (substr (strcase AppNam) 1 5) "ADDSP")
	(C:Fdr_Grey)
	(setq	LodVer	"1.50g")
)
(setq	LodVer	"1.50g")
