(if AppNam								; Code Version Indicator
	(princ (strcat "\n" AppNam " NoMasks Loading."))
	(princ "\nAddsPlot NoFills Loading.")
)

(defun NoFills ( / )
	(command "_.Mspace")
	(command "_.-layer" "F" "*-LM-*" "")
	(command "_.-layer" "F" "*-AA-*" "")
	(command "_.-layer" "F" "*-AB-*" "")
	(command "_.-layer" "F" "*-WA-*" "")
	(command "_.-layer" "F" "*-AC-*" "")
	(command "_.-layer" "F" "*-TA-*" "")
	(princ)
)

(if (= (substr (strcase AppNam) 1 5) "ADDSP")
	(NoFills)
	(setq	LodVer	"1.50")
)
