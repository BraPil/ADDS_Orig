(if AppNam								; Code Version Indicator
	(princ (strcat "\n" AppNam " View4Sw Loading."))
	(princ "\nAddsPlot View4Sw Loading.")
)

(defun Viewsub2	( /	Eset swlist n Ename		; Builds a SWITCH file, listing number & XY
					swnum swscale sw vname	; location, sorts, then builds a view for each switch.
					vXcord vYcord vdist		; format of swlist is vname=8chr, vXcord=7chr, vYcord=8chr, vdist=3chr
					cmdE maxS LNam )
	(if Bug (princ "\n{Viewsub2 entered\n"))
	(if (= (getvar "UNDOCTL") 0)
		(command "_.UNDO" "N")
		(if (= (getvar "UNDOCTL") 3)
			(command "_.UNDO" "C" "N")
		)
	)
	(setq	cmdE		(getvar "CMDECHO"))
	(setq	maxS		(getvar "MAXSORT"))
	(if (not Bug)
		(setvar "CMDECHO" 0)
		(setvar "CMDECHO" 1)
	)
	(if	(setq	Eset	(ssget "X"	(list		cons 0 "?TEXT")
											(cons -4 "<AND")
													(cons 40 0.7)
											(cons -4 "AND>")
								)
					)
		)
		(progn
			(setq	swlist	(list )
					n		0
			)
			(while (setq Ename (ssname Eset n))
				(if (= (cdr (assoc 66 (entget Ename))) 1)
					(progn
						(setq	swnum	(cdr (assoc 1 (entget (entnext Ename))))
						)
						(if  (and (> (strlen swnum) 2) (not (wcmatch swnum "*`,* *,*`#*,*`.*,*` *,*`/*,*`?*,)))
							(setq	swlist	(cons	(strcat	(substr (strcat swnum "        ") 1 8)
															(substr (strcat (itoa (fix (cadr (assoc 10 (entget Ename))))) "          ") 1 7)
															(substr (strcat (itoa (fix (caddr(assoc 10 (entget Ename))))) "          ") 1 8)
															(substr (strcat (rtos swscale) "          ") 1 3)
													)
													swlist
											)
							)
						)
					)
				)
				(setq	n	(1+ n))
			)
			(setq	swlist	(acad_strlsort swlist))
			(foreach	sw
					swlist
					(setq	vname	(rtrim (substr sw 1 8))
							vXcord	(- (atof (substr sw 9 7)) xbase)
							vYcord	(- (atof (substr sw 16 8)) ybase)
							vdist	50.0
					)
					(command "_.VIEW" "W" vname (list (- vXcord vdist) (- vYcord vdist)) (list (+ vXcord vdist) (+ vYcord vdist)))
			)
		)
	)
	(setvar "CMDECHO" cmdE)
	(setvar "MAXSORT" maxS)
	(if Bug (princ "\nViewsub2 exited}\n"))
	(princ)
)

(if (= (substr (strcase AppNam) 1 5) "ADDSP")
	(View4Sw)
	(setq	LodVer	"1.50a")
)
