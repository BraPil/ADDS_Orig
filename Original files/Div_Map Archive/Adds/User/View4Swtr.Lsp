(if AppNam								; Code Version Indicator
	(princ (strcat "\n" AppNam " View4Sw Loading."))
	(princ "\nAddsPlot View4Sw Loading.")
)

(defun RTrim ( StrIn /	n )					;--Returns variable passed after trimming off any trailing spaces--
	(setq	n	(strlen StrIn))
	(while	(and	(> n 0)
				(= (substr StrIn n 1) " ")
			)
		(setq	n	(1- n))
	)
	(if (> n 0)
		(substr StrIn 1 n)
		StrIn
	)
)

(defun View4Sw	( /	Eset swlist n Ename		; Builds a SWITCH file, listing number & XY
					swnum swscale sw vname	; location, sorts, then builds a view for each switch.
					vXcord vYcord vdist		; format of swlist is vname=8chr, vXcord=7chr, vYcord=8chr, vdist=3chr
					cmdE maxS LNam )
	(if Bug (princ "\n{View4Sw entered\n"))
	(if (= (getvar "UNDOCTL") 0)
		(command "_.UNDO" "N")
		(if (= (getvar "UNDOCTL") 3)
			(command "_.UNDO" "C" "N")
		)
	)
	(setq	cmdE		(getvar "CMDECHO"))
	(setq	maxS		(getvar "MAXSORT"))
	(if (not Bug)
		(setvar "CMDECHO" 0)
		(setvar "CMDECHO" 1)
	)
	(if (and (= "AddsPlot" AppNam) (/= 0 (getvar "tilemode")))
		(command "_.tilemode" 0)
	)
	(if (and (= "AddsPlot" AppNam) (= 1 (getvar "cvport")))
		(command "_.MSpace")
	)
	(if Div
		(if (= Div "W_")
			(if (setq x (ssget "X" (list (cons 8 "????FL*")))) (command "_.ERASE" x ""))	; Gets rid of fill lines
		)
	)
	(if	(setq	Eset	(ssget "X"	(list	(cons -4 "<OR")
											(cons -4 "<AND")
												(cons 0 "INSERT")
											(cons -4 "<OR")
												(cons 8 "????SW-*")
												(cons 8 "????XF-*")
											(cons -4 "OR>")
											(cons -4 "AND>")
											(cons -4 "<AND")
												(cons 0 "INSERT")
												(cons -4 "<OR")
													(cons 2 "RECL*")
													(cons 2 "_OCR*")
													(cons 2 "A105")
													(cons 2 "A169")
													(cons 2 "A193")
													(cons 2 "A194")
												(cons -4 "OR>")
												(cons 8 "????CK-*")
											(cons -4 "AND>")
										(cons -4 "OR>")
								)
					)
		)
		(progn
			(setq	swlist	(list )
					n		0
			)
			(while (setq Ename (ssname Eset n))
				(if (= (cdr (assoc 66 (entget Ename))) 1)
					(progn
						(setq	swnum	(cdr (assoc 1 (entget (entnext Ename))))
								swscale	(cdr (assoc 41 (entget Ename)))
								LNam		(cdr (assoc 8 (entget Ename)))
						)
						(if (and Bug LNam swnum)
							(princ (strcat "\n[Bug] Layer:{" LNam "} SwNum:{" swnum "}"))
						)
						(if	(member	(cdr (assoc 2 (entget Ename)))
									(list "NEWSS" "_SS" "_SSR" "A125S" "A170S")
							)
							(setq	swscale	(* swscale 4))
						)
						(if (and (>= (strlen swnum) 1) (not (wcmatch swnum "*`,*,* *,*`#*,*.*,LFSP,PDMT,*KVAR")))
							(setq	swlist	(cons	(strcat	(substr (strcat swnum "        ") 1 8)
															(substr (strcat (itoa (fix (cadr (assoc 10 (entget Ename))))) "          ") 1 7)
															(substr (strcat (itoa (fix (caddr(assoc 10 (entget Ename))))) "          ") 1 8)
															(substr (strcat (itoa (fix swscale)) "          ") 1 3)
													)
													swlist
											)
							)
						)
					)
				)
				(setq	n	(1+ n))
			)
			(setq	swlist	(acad_strlsort swlist))
			(foreach	sw
					swlist
					(setq	vname	(rtrim (substr sw 1 8))
							vXcord	(atoi (substr sw 9 7))
							vYcord	(atoi (substr sw 16 8))
							vdist	(* (atoi (substr sw 24 3)) 10)
					)
					(command "_.VIEW" "W" vname (list (- vXcord vdist) (- vYcord vdist)) (list (+ vXcord vdist) (+ vYcord vdist)))
			)
		)
	)
	;	Cleanup
	(setvar "CMDECHO" cmdE)
	(setvar "MAXSORT" maxS)
	(if x	(setq x	nil))
	(if Eset	(setq Eset	nil))
	(gc)
	
	(if Bug (princ "\nView4Sw exited}\n"))
	(princ)
)

(if (= (substr (strcase AppNam) 1 5) "ADDSP")
	(View4Sw)
	(setq	LodVer	"3.0.0")
)
