(if AppNam								; Code Version Indicator
	(princ (strcat "\n" AppNam " Quads Loading."))
	(princ "\nAddsPlot Quads Loading.")
)

(defun C:Quads ( / )
	(if (not Bld_DLG_Lst)
		(load "DlgLod")
	)
	(if (not ViewPorter)
		(load "Utils")
	)
	(if (/= 1 (getvar "cvport"))
		(command "_.tilemode" 0)
	)
	(setq	ViewLst	(ViewPorter)
			M_LL		(nth 8 ViewLst)
			M_UR		(nth 9 ViewLst)
	)
	(if (/= 0 (getvar "tilemode"))		
		(command "_.tilemode" 0)
	)
	(if (= 1 (getvar "cvport"))
		(command "_.MSpace")
	)
	(DoBackDLG M_LL M_UR 2)
	(command "_.tilemode" 1)			; 10-27-09 change forcing tilemode from 0 to 1 for LCSp1.lst to work correctly.
	(princ)
)

(if (= (substr (strcase AppNam) 1 5) "ADDSP")
	(C:Quads)
	(setq	LodVer	"3.00a")
)
