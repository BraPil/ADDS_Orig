(if AppNam								; Code Version Indicator
	(princ (strcat "\n" AppNam " View4SwL Loading."))
	(princ "\nAddsPlot View4SwL Loading.")
)

(defun View4SwL	( /	;Eset swlist Cnt Ename	; Builds a SWITCH file, listing number & XY
					;swnum swscale sw vname	; location, sorts, then builds a view for each switch.
					;vXcord vYcord vdist		; format of swlist is vname=8chr, vXcord=7chr, vYcord=8chr, vdist=3chr
					;cmdE maxS HeadA HeadB HeadC Filt1 Filt2 FiltA FiltB MyKey LNam )
					)
	(if Bug (princ "\n{View4SwL entered\n"))
	(if (= (getvar "UNDOCTL") 0)
		(command "_.UNDO" "N")
		(if (= (getvar "UNDOCTL") 3)
			(command "_.UNDO" "C" "N")
		)
	)
	(setq	cmdE		(getvar "CMDECHO")
			maxS		(getvar "MAXSORT")
			HeadA	(list	(cons -4 "<OR")
							(cons -4 "<AND")
							(cons 0 "INSERT")
					)
			HeadB	(list	(cons -4 "AND>")
							(cons -4 "<AND")
							(cons 0 "INSERT")
							(cons 2 "A169,A105")
					)
			HeadD	(list	(cons -4 "AND>")
							(cons -4 "<AND")
							(cons 0 "INSERT")
							(cons 2 "A193,A194")
					)
			HeadC	(list	(cons -4 "AND>")
							(cons -4 "OR>")
					)
	)
	(setvar "MAXSORT" 32767)
	(if Bug
		(setvar "CMDECHO" 1)
		(setvar "CMDECHO" 0)
	)
	(if pldname
		(if (= (substr (strcase pldname) 1 3) "OSD")
			(setq	VHgt		2)
			(setq	VHgt		10)
		)
		(setq	VHgt		10)
	)
	(if (and (= "AddsPlot" AppNam) (/= 0 (getvar "tilemode")))
		(command "_.tilemode" 0)
	)
	(if (and (= "AddsPlot" AppNam) (= 1 (getvar "cvport")))
		(command "_.MSpace")
	)
	(if (not CordFile)
		(setq	CordFile	"Nothing")
	)
	(if Div
		(if (= Div "W_")
			(if (setq x (ssget "X" (list (cons 8 "????FL*")))) (command "_.ERASE" x ""))	; Gets rid of fill lines
		)
	)
	(cond
		((= (strcase CordFile) "SUB")
			(if (setq MyKey (ValiStrLst CordKey 2))
				(setq	Filt1	(mapcar (quote (lambda (x) (cons 8 (strcat x "??SW-*")))) MyKey)
						Filt2	(mapcar (quote (lambda (x) (cons 8 (strcat x "??CK-*")))) MyKey)
						FiltA	(cons (cons -4 "OR>") (reverse Filt1))
						FiltA	(cons (cons -4 "<OR") (reverse FiltA))
						FiltB	(cons (cons -4 "OR>") (reverse Filt2))
						FiltB	(cons (cons -4 "<OR") (reverse FiltB))
						FiltR	(append HeadA FiltA)
						FiltR	(append FiltR HeadB)
						FiltR	(append FiltR FiltB)
						FiltR	(append FiltR HeadD)
						FiltR	(append FiltR FiltB)
						FiltR	(append FiltR HeadC)
						Eset		(ssget "X" FiltR)
				)
				(setq	Eset	(ssget "X"	(list	(cons -4 "<OR")
													(cons -4 "<AND")
														(cons 0 "INSERT")
														(cons -4 "<OR")
															(cons 8 "????SW-*")
															(cons 8 "????XF-*")
															(cons 8 "EUF")
															(cons 8 "EOF")
															(cons 8 "RED")
															(cons 8 "BLUE")
															(cons 8 "GREEN")
															(cons 8 "CYAN")
															(cons 8 "M*")
														(cons -4 "OR>")
													(cons -4 "AND>")
													(cons -4 "<AND")
														(cons 0 "INSERT")
														(cons -4 "<OR")
															(cons 2 "RECL*")
															(cons 2 "_OCR*")
															(cons 2 "A105")
															(cons 2 "A169")
															(cons 2 "A193")
															(cons 2 "A194")
															(cons 2 "ESWNO")
															(cons 2 "ESTN")
															(cons 2 "RSTN")
															(cons 2 "STATION")
														(cons -4 "OR>")
														(cons 8 "????CK-*")
													(cons -4 "AND>")
												(cons -4 "OR>")
										)
							)
				)
			)
		)
		((= (strcase CordFile) "FEEDER")
			(if (setq MyKey (ValiStrLst CordKey 3))
				(setq	Filt1	(mapcar (quote (lambda (x) (cons 8 (strcat x "?SW-*")))) MyKey)
						Filt2	(mapcar (quote (lambda (x) (cons 8 (strcat x "?CK-*")))) MyKey)
						FiltA	(cons (cons -4 "OR>") (reverse Filt1))
						FiltA	(cons (cons -4 "<OR") (reverse FiltA))
						FiltB	(cons (cons -4 "OR>") (reverse Filt2))
						FiltB	(cons (cons -4 "<OR") (reverse FiltB))
						FiltR	(append HeadA FiltA)
						FiltR	(append FiltR HeadB)
						FiltR	(append FiltR FiltB)
						FiltR	(append FiltR HeadD)
						FiltR	(append FiltR FiltB)
						FiltR	(append FiltR HeadC)
						Eset		(ssget "X" FiltR)
				)
				(setq	Eset	(ssget "X"	(list	(cons -4 "<OR")
													(cons -4 "<AND")
														(cons 0 "INSERT")
														(cons 8 "????SW-*")
													(cons -4 "AND>")
													(cons -4 "<AND")
														(cons 0 "INSERT")
														(cons 2 "RECL*")
														(cons 8 "????CK-*")
													(cons -4 "AND>")
													(cons -4 "<AND")
														(cons 0 "INSERT")
														(cons 2 "_OCR*")
														(cons 8 "????CK-*")
													(cons -4 "AND>")
													(cons -4 "<AND")
														(cons 0 "INSERT")
														(cons 2 "A105,A169")
														(cons 8 "????CK-*")
													(cons -4 "AND>")
													(cons -4 "<AND")
														(cons 0 "INSERT")
														(cons 2 "A193,A194")
														(cons 8 "????CK-*")
													(cons -4 "AND>")
												(cons -4 "OR>")
										)
							)
				)
			)
		)
		(T
			(setq	Eset	(ssget "X"	(list	(cons -4 "<OR")
												(cons -4 "<AND")
													(cons 0 "INSERT")
													(cons 8 "????SW-*")
												(cons -4 "AND>")
												(cons -4 "<AND")
													(cons 0 "INSERT")
													(cons 2 "RECL*")
													(cons 8 "????CK-*")
												(cons -4 "AND>")
												(cons -4 "<AND")
													(cons 0 "INSERT")
													(cons 2 "_OCR*")
													(cons 8 "????CK-*")
												(cons -4 "AND>")
												(cons -4 "<AND")
													(cons 0 "INSERT")
													(cons 2 "A105,A169")
													(cons 8 "????CK-*")
												(cons -4 "AND>")
												(cons -4 "<AND")
													(cons 0 "INSERT")
													(cons 2 "A193,A194")
													(cons 8 "????CK-*")
												(cons -4 "AND>")
											(cons -4 "OR>")
									)
						)
			)
		)
	)
	(if Eset
		(progn
			(setq	swlist	(list )
					Bubba	(princ (strcat "\nView4SwL is working {" (itoa (sslength Eset)) "} switches..."))
					Cnt		0
			)
			(while (setq Ename (ssname Eset Cnt))
				(if (= (cdr (assoc 66 (entget Ename))) 1)
					(progn
						(setq	swnum	(cdr (assoc 1 (entget (entnext Ename))))
								swscale	(cdr (assoc 41 (entget Ename)))
								LNam		(cdr (assoc 8 (entget Ename)))
						)
						(if (or 
							   (= (cdr (assoc 2 (entget Ename))) "ESTN")
							   (= (cdr (assoc 2 (entget Ename))) "STATION")
							)
								(if (<= (strlen swnum) 2)
								   (progn
										(setq ename1(cdr (assoc -1(entget (entnext Ename)))))
										(setq swnum (strcat swnum (cdr (assoc 1 (entget (entnext Ename1))))))
									)
								)
						)
						(if (and Bug LNam swnum)
							(princ (strcat "\n[Bug] Layer:{" LNam "} SwNum:{" swnum "}"))
						)
						(if	(member	(cdr (assoc 2 (entget Ename)))
									(list "NEWSS" "_SS" "_SSR" "A125S" "A170S")
							)
							(setq	swscale	(abs (* swscale 2)))
						)
						(StpBadChar swnum 1)
						(if  (and (>= (strlen swnum) 1) (not (wcmatch swnum "*`,* *,*`#*,*`.*,*` *,*`/*,*`?*,*`%*,*`)*,*`(*,*`-*,*`**,*`\*,LFSP,PDMT,*KVAR")))
							(setq	swlist	(cons	(strcat	(substr (strcat (StpBadChar swnum 1) "        ") 1 8)
															(substr (strcat (itoa (fix (cadr (assoc 10 (entget Ename))))) "          ") 1 7)
															(substr (strcat (itoa (fix (caddr(assoc 10 (entget Ename))))) "          ") 1 8)
															(substr (strcat (rtos swscale) "          ") 1 3)
													)
													swlist
											)
							)
						)
					)
				)
				(setq	Cnt	(1+ Cnt))
			)
			(if Bug (princ (strcat "\n{Bug: swlist has [" (itoa (length swlist)) "] members.}\n")))
			(setq	swlist	(acad_strlsort swlist))
			(if Bug (princ "\n{Bug: swlist is sorted}\n"))
			(foreach	sw
					swlist
					(if Bug (princ (strcat "\n{Bug: swlist working [" sw "]}\n")))
					(setq	vname	(rtrim (substr sw 1 8))
							Bubba	(if Bug (princ (strcat "\n{Bug: vname=[" vname "]}\n")))
							vXcord	(atoi (substr sw 9 7))
							Bubba	(if Bug (princ (strcat "\n{Bug: vXcord=[" (itoa vXcord) "]}\n")))
							vYcord	(atoi (substr sw 16 8))
							Bubba	(if Bug (princ (strcat "\n{Bug: vYcord=[" (itoa vYcord) "]}\n")))
							vdist	(* (atoi (substr sw 24 3)) VHgt)
							Bubba	(if Bug (princ (strcat "\n{Bug: vdist=[" (itoa vdist) "]}\n")))
					)
					(if (equal vdist 0.0 1.0)
						(setq vdist (* sf 2))
					)
					(command "_.VIEW" "W" vname (list (- vXcord vdist) (- vYcord vdist)) (list (+ vXcord vdist) (+ vYcord vdist)))
			)
		)
	)
	(setvar "CMDECHO" cmdE)
	(setvar "MAXSORT" maxS)
	(if Bug (princ "\nView4SwL exited}\n"))
	;	Cleanup
	(if x
		(progn
			(setq x nil)
			(gc)
		)
	)
	(if Eset
		(progn
			(setq x Eset)
			(gc)
		)
	)
	(princ)
)

(if (= (substr (strcase AppNam) 1 5) "ADDSP")
	(View4SwL)
	(setq	LodVer	"1.50d")
)
