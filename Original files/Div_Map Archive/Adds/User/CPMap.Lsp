(if AppNam								; Code Version Indicator
	(princ (strcat "\n" AppNam " CPMap Loading."))
	(princ "\nAddsPlot CPMap Loading.")
)

(defun CPMap ( /	CKcol )
	(princ "\nRunning CPs2Blu")
	(load (strcat _path-user "cps2blu"))
	(cond
		((= Div "E_")
			(setq	CKcol	"1")
		 	(command "_.Layer" "C" CKcol "????[CFS][KLW]*" "")
			(princ "\nRunning Fdr_Grey")
			(load (strcat _path-user "fdr_grey"))
			(princ "\nRunning ThinUG")
			(load (strcat _path-user "thinug"))
		)
		((= Div "M_")
			(princ "\nRunning Fdr_Only")
			(load (strcat _path-user "Fdr_Only"))
		)
		(T
			(princ "\nRunning Fdr_Grey")
			(load (strcat _path-user "fdr_grey"))
			(princ "\nRunning ThinUG")
			(load (strcat _path-user "thinug"))
		)
	)
	(princ "\nDone Running CPMap!")
)

(if (= (substr (strcase AppNam) 1 5) "ADDSP")
	(CPMap)
	(setq	LodVer	"1.50a")
)
