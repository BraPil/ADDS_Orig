(if AppNam								; Code Version Indicator
	(princ (strcat "\n" AppNam " View4Sw Loading."))
	(princ "\nAddsPlot View4Sw Loading.")
)

(defun View4Sw	( /	Eset swlist n Ename		; Builds a SWITCH file, listing number & XY
					swnum swscale sw vname	; location, sorts, then builds a view for each switch.
					vXcord vYcord vdist		; format of swlist is vname=8chr, vXcord=7chr, vYcord=8chr, vdist=3chr
					cmdE maxS LNam )
	(command "zoom" "E")
	(if Bug (princ "\n{View4Sw entered\n"))
	(if (= (getvar "UNDOCTL") 0)
		(command "_.UNDO" "N")
		(if (= (getvar "UNDOCTL") 3)
			(command "_.UNDO" "C" "N")
		)
	)
	(setq	cmdE		(getvar "CMDECHO"))
	(setq	maxS		(getvar "MAXSORT"))
	(if (not Bug)
		(setvar "CMDECHO" 0)
		(setvar "CMDECHO" 1)
	)
	(if (and (= "AddsPlot" AppNam) (/= 0 (getvar "tilemode")))
		(command "_.tilemode" 0)
	)
	(if (and (= "AddsPlot" AppNam) (= 1 (getvar "cvport")))
		(command "_.MSpace")
	)
	(setvar "MAXSORT" 32767)
	(if Div
		(if (= Div "W_")
			(if (setq x (ssget "X" (list (cons 8 "????FL*")))) (command "_.ERASE" x ""))	; Gets rid of fill lines
		)
	)
	(if	(setq	Eset	(ssget "X"	(list	(cons -4 "<OR")
											(cons -4 "<AND")
												(cons 0 "INSERT")
												(cons -4 "<OR")
													(cons 8 "????SW*")
													(cons 8 "????XF*")
													(cons 8 "EUF*")
													(cons 8 "RUF")
													(cons 8 "EED")
													(cons 8 "EOF")
													(cons 8 "EOB")
													(cons 8 "IOB")
													(cons 8 "IUF")
													(cons 8 "CUF")
													(cons 8 "EOB")
													(cons 8 "R8")
													(cons 8 "R1")
													(cons 8 "R2")
													(cons 8 "R3")
													(cons 8 "R4")
													(cons 8 "R5")
													(cons 8 "R6")
													(cons 8 "R7")
													(cons 8 "R*")
													(cons 8 "B*")
													(cons 8 "G*")
													(cons 8 "CYAN")
													(cons 8 "O*")
													(cons 8 "DKRED")
													(cons 8 "PURPLE")
													(cons 8 "MAG*")
													(cons 8 "M")
													(cons 8 "CKT*")
													(cons 8 "MT")
													(cons 8 "ELACK")
												(cons -4 "OR>")
											(cons -4 "AND>")
											(cons -4 "<AND")
												(cons 0 "INSERT")
												(cons -4 "<OR")
													(cons 2 "RECL*")
													(cons 2 "_OCR*")
													(cons 2 "A105")
													(cons 2 "A169")
													(cons 2 "A193")
													(cons 2 "A194")
													(cons 2 "ESWNO")
													(cons 2 "ESTN")
													(cons 2 "CSTN")
													(cons 2 "RSTN")
													(cons 2 "ISTN")
													(cons 2 "STATION*")
													(cons 2 "SWITCHNO")
												(cons -4 "OR>")
												(cons 8 "????CK-*")
											(cons -4 "AND>")
										(cons -4 "OR>")
								)
					)
			)
		(progn
			(setq	swlist	(list )
					n		0
			)
			(while (setq Ename (ssname Eset n))
				(if (= (cdr (assoc 66 (entget ename))) 1)
					(progn
						(setq	swnum	(cdr (assoc 1 (entget (entnext Ename))))
								swscale	(cdr (assoc 41 (entget Ename)))
								LNam		(cdr (assoc 8 (entget Ename)))
						)
						(princ swnum)
						(if (or 
							   (= (cdr (assoc 2 (entget Ename))) "CSTN")	
							   (= (cdr (assoc 2 (entget Ename))) "ESTN")
							   (= (cdr (assoc 2 (entget Ename))) "ISTN")
							   (= (cdr (assoc 2 (entget Ename))) "RSTN")
							   (= (cdr (assoc 2 (entget Ename))) "STATION")
							)
								(if (and (<= (strlen swnum) 2) (/= swnum  " "))
								   (progn
										(setq ename1(cdr (assoc -1(entget (entnext Ename)))))
										(setq swnum (strcat swnum (cdr (assoc 1 (entget (entnext Ename1))))))
									)
								   (progn
										(setq ename1(cdr (assoc -1(entget (entnext Ename)))))
										(setq swnum (cdr (assoc 1 (entget (entnext Ename1)))))
									)
								)
						)
						(if (and Bug LNam swnum)
							(princ (strcat "\n[Bug] Layer:{" LNam "} SwNum:{" swnum "}"))
						)
						(if	(member	(cdr (assoc 2 (entget Ename)))
									(list "NEWSS" "_SS" "_SSR" "A125S" "A170S")
							)
							(setq	swscale	(abs (* swscale 2)))
						)
						(if swnum
							(if  (and (> (strlen swnum) 2) (not (wcmatch swnum "*`,* *,*`#*,*`.*,*` *,*`/*,*`?*,*`%*,*`(*,*`)*,LFSP,PDMT,*KVAR")))
								(setq	swlist	(cons	(strcat	(substr (strcat swnum "        ") 1 8)
																(substr (strcat (itoa (fix (cadr (assoc 10 (entget Ename))))) "          ") 1 7)
																(substr (strcat (itoa (fix (caddr(assoc 10 (entget Ename))))) "          ") 1 8)
																(substr (strcat (rtos swscale) "          ") 1 3)
														)
														swlist
												)
								)
							)
						)
					)
				)
				(setq	n	(1+ n))
			)
			(setq ibase (getvar "INSBASE")
				 xbase (car ibase)
				 ybase (cadr ibase)
			)
			(setq	swlist	(acad_strlsort swlist))
			(foreach	sw
					swlist
					(setq	vname	(rtrim (substr sw 1 8))
							vXcord	(- (atof (substr sw 9 7)) xbase)
							vYcord	(- (atof (substr sw 16 8)) ybase)
							vdist	(* (atof (substr sw 24 3)) 5)
					)
					(if (equal vdist 0.0 1.0)
						(setq vdist (* SF 2.0))
					)
					(if (null (tblsearch "VIEW" vname))
						(progn
							(command "_.VIEW" "W" vname (list (- vXcord vdist) (- vYcord vdist)) (list (+ vXcord vdist) (+ vYcord vdist)))
							(setq dev_no vname
								 outputfil "C:/master.txt"
								 outfil(open outputfil "a")
								 NewSS	(ssget "X"	(list	(cons 0 "INSERT")
															(cons 2 "[ABCDEFX]SHEET")
													)
										)
								 len (strlen _path-dwf)
								 ctr 1
								 pth_dwf ""
							)
							(repeat len
								(setq char_chk (substr _path-dwf ctr 1))
									(if (= char_chk "/")
										(setq char_chk "\\")
									)
						   		(setq pth_dwf (strcat pth_dwf char_chk)
									 ctr (+ ctr 1)
								)
							)
							(if newss
								(progn
								 	(setq item  (ssname newss 0)
								 	  	 ent	  (entget item)
									 	 attent(entget(entnext(cdr(assoc -1 ent))))
									 	 job   (cdr (assoc 1 attent))
									)
									(repeat 2
										(setq attent(entget(entnext(cdr(assoc -1 attent)))))
		   						 		(if (= (cdr (assoc 2 attent)) "DETAIL1")
											(setq det1 (cdr (assoc 1 attent)))
											(setq det2 (cdr (assoc 1 attent)))
							    			)
									)
									(setq title (strcat job " " det1 " " det2))
								)
								(setq title " ")
							)
		   					(setq dwg_no (getvar "DWGNAME")
								 dwf_no (strcat (substr dwg_no 1 (- (strlen dwg_no) 1)) "f")
								 dev_no_pth (strcat dev_no ";" (getvar "DWGPREFIX") ";"  (getvar "DWGNAME") ";" pth_dwf ";" dwf_no ";" title)
							)
							(write-line dev_no_pth outfil)
							(close outfil)
						)
					)
			)
		)
	)
	(c:shvw)
	(setvar "CMDECHO" cmdE)
	(setvar "MAXSORT" maxS)
	(if Bug (princ "\nView4Sw exited}\n"))
	(princ)
)
	(if (= (substr (strcase AppNam) 1 5) "ADDSP")
		(View4Sw)
		(setq	LodVer	"1.50a")
	)
