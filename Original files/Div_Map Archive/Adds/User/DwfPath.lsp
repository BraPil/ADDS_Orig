(if AppNam								; Code Version Indicator
	(princ (strcat "\n" AppNam " DwfPath Loading."))
	(princ "\nAddsPlot DwfPath Loading.")
)

(defun DwfPath ( / )
	(cond
		((= Div "BH")
			(setq	_Path-DWF	"\\\\GAXGPSW03\\PowerDel$\\APC\\DIV\\BD\\DWF\\")
			(princ "\nPath for DWF publication set to Birmingham Div default.")
		)
		((= Div "E_")
			(setq	_Path-DWF	"\\\\GAXGPSW03\\PowerDel$\\APC\\DIV\\ED\\DWF\\")
			(princ "\nPath for DWF publication set to Eastern Div default.")
		)
		((= Div "M_")
			(setq	_Path-DWF	"\\\\GAXGPSW03\\PowerDel$\\APC\\DIV\\MOB\\DWF\\")
			(princ "\nPath for DWF publication set to Mobile Div default.")
		)
		((= Div "S_")
			(setq	_Path-DWF	"\\\\GAXGPSW03\\PowerDel$\\APC\\DIV\\SD\\DWF\\")
			(princ "\nPath for DWF publication set to Southern Div default.")
		)
		((= Div "SE")
			(setq	_Path-DWF	"\\\\GAXGPSW03\\PowerDel$\\APC\\DIV\\SD\\DWF\\")
			(princ "\nPath for DWF publication set to Southern Div default.")
		)
		((= Div "W_")
			(setq	_Path-DWF	"\\\\GAXGPSW03\\PowerDel$\\APC\\DIV\\WD\\DWF\\")
			(princ "\nPath for DWF publication set to Western Div default.")
		)
	)
)

(if (= (substr (strcase AppNam) 1 5) "ADDSP")
	(DwfPath)
	(setq	LodVer	"2.0.0")
)
