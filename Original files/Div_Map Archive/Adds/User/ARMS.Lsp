(if AppNam								; Code Version Indicator
	(princ (strcat "\n" AppNam " Arms Loading."))
	(princ "\nAddsPlot Arms Loading.")
)

(defun C:Arms ( / )
	(if (/= 0 (getvar "tilemode"))
		(command "_.tilemode" 0)
	)
	(if (= 1 (getvar "cvport"))
		(command "_.MSpace")
	)
	(cond
		((equal (strcat pldname) "ARMSD05")
			(command "_.Insert" "*S:\\WorkGroups\\APC Southern Division\\Division Mapping\\Adds\\PANEL\\6543620.dwg" "0,0" "" "")
			(command "_.Insert" "*S:\\WorkGroups\\APC Southern Division\\Division Mapping\\Adds\\PANEL\\6543612.dwg" "0,0" "" "")
			(command "_.Insert" "*S:\\WorkGroups\\APC Southern Division\\Division Mapping\\Adds\\PANEL\\6543608.dwg" "0,0" "" "")
			(command "_.Insert" "*S:\\WorkGroups\\APC Southern Division\\Division Mapping\\Adds\\PANEL\\6543604.dwg" "0,0" "" "")
			(command "_.Insert" "*S:\\WorkGroups\\APC Southern Division\\Division Mapping\\Adds\\PANEL\\6543596.dwg" "0,0" "" "")
			(command "_.Insert" "*S:\\WorkGroups\\APC Southern Division\\Division Mapping\\Adds\\PANEL\\6483596.dwg" "0,0" "" "")
			(command "_.Insert" "*S:\\WorkGroups\\APC Southern Division\\Division Mapping\\Adds\\PANEL\\6483600.dwg" "0,0" "" "")
			(command "_.Insert" "*S:\\WorkGroups\\APC Southern Division\\Division Mapping\\Adds\\PANEL\\6483604.dwg" "0,0" "" "")
			(command "_.Insert" "*S:\\WorkGroups\\APC Southern Division\\Division Mapping\\Adds\\PANEL\\6483608.dwg" "0,0" "" "")
			(command "_.Insert" "*S:\\WorkGroups\\APC Southern Division\\Division Mapping\\Adds\\PANEL\\6483612.dwg" "0,0" "" "")
		)
	)
	(if (= Div "M_")
		(if Desc_1
			(progn
				(load (strcat _PATH-USER "SymColor"))
				(setq	Desc_1	nil)
			)
		)
	)
	(load (strcat _path-user "View4SwL"))
	(load (strcat _path-user "View4Cap"))
	(load (strcat _path-user "NoFills"))
	(load (strcat _path-user "Quads"))
	(princ)
)

(if (= (substr (strcase AppNam) 1 5) "ADDSP")
	(C:Arms)
	(setq	LodVer	"1.50")
)
