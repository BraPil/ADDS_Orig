(if AppNam								; Code Version Indicator
	(princ (strcat "\n" AppNam " View4Cadet Loading."))
	(princ "\nAddsPlot View4Cadet Loading.")
)

(defun C:View4Cadet	( /	Eset n Ename		; Builds a SWITCH file, listing number & XY
					swnum swscale sw vname	; location, sorts, then builds a view for each switch.
					vXcord vYcord vdist		; format of swlist is vname=8chr, vXcord=7chr, vYcord=8chr, vdist=3chr
					cmdE maxS LNam )	;swlist 
	(if Bug (princ "\n{View4Cadet entered\n"))
	(if (= (getvar "UNDOCTL") 0)
		(command "_.UNDO" "N")
		(if (= (getvar "UNDOCTL") 3)
			(command "_.UNDO" "C" "N")
		)
	)
	(setq	cmdE		(getvar "CMDECHO"))
	(setq	maxS		(getvar "MAXSORT"))
	(if (not Bug)
		(setvar "CMDECHO" 0)
		(setvar "CMDECHO" 1)
	)
	(if Div
		(if (= Div "W_")
			(if (setq x (ssget "X" (list (cons 8 "????FL*")))) (command "_.ERASE" x ""))	; Gets rid of fill lines
		)
	)
	(setvar "MAXSORT" 32767)
	(if	(setq	Eset	(ssget "X"	(list	(cons 0 "INSERT")
								)
					)
		)
		(progn
			(setq	swlist	(list )
					n		0
			)
			(while (setq Ename (ssname Eset n))
				(if (= (cdr (assoc 66 (entget Ename))) 1)
					(progn
						(setq	swnum	(cdr (assoc 1 (entget (entnext Ename))))
								swscale	(cdr (assoc 41 (entget Ename)))
								LNam		(cdr (assoc 8 (entget Ename)))
						)
						(if (= (cdr (assoc 0 (entget (entnext (entnext Ename))))) "ATTRIB")
							(setq	swnum2	(cdr (assoc 1 (entget (entnext (entnext Ename))))))
							(setq	swnum2	nil)
						)
						(if swnum
							(setq	swnum	(ReplBadChars swnum))
						)
						(if swnum2
							(setq	swnum2	(ReplBadChars swnum2))
						)
						(if (and Bug LNam swnum swnum2)
							(princ (strcat "\n[Bug] Layer:{" LNam "} SwNum:{" swnum "} SwNum2:{" swnum2 "}"))
							(if (and Bug LNam swnum)
								(princ (strcat "\n[Bug] Layer:{" LNam "} SwNum:{" swnum "}"))
							)
						)
						(if (and LNam swnum swnum2)
							(if	(and	(>= (strlen swnum) 1)
									(not (wcmatch swnum "*`/*,*`,*,*`#*,* *,LFSP,PDMT,*KVAR"))
									(>= (strlen swnum2) 1)
									(not (wcmatch swnum2 "*`/*,*`,*,*`#*,* *,LFSP,PDMT,*KVAR"))
								)
								(setq	swnum	(strcat swnum "-" swnum2))
							)
						)
						(if	swscale
							(if (>= swscale 2.0)
								(setq	swscale	(/ swscale 2))
								(setq	swscale	1.0)
							)
						)
						(if (and (>= (strlen swnum) 1) (not (wcmatch swnum "*`/*,*`,*,*`#*,* *,LFSP,PDMT,*KVAR"))) ;"*`,*,* *,*`#*,*.*,LFSP,PDMT,*KVAR"
							(setq	swlist	(cons	(strcat	(substr (strcat swnum "        ") 1 8)
															(substr (strcat (itoa (fix (cadr (assoc 10 (entget Ename))))) "          ") 1 7)
															(substr (strcat (itoa (fix (caddr(assoc 10 (entget Ename))))) "          ") 1 8)
															(substr (strcat (itoa (fix swscale)) "          ") 1 3)
													)
													swlist
											)
							)
							(if (and swnum Bug)
								(princ (strcat "\nRejecting swnum {" swnum "}\n"))
							)
						)
					)
				)
				(setq	n	(1+ n))
			)
			(setq	swlist	(acad_strlsort swlist))
			(foreach	sw
					swlist
					(setq	vname	(rtrim (substr sw 1 8))
							vXcord	(atoi (substr sw 9 7))
							vYcord	(atoi (substr sw 16 8))
							vdist	(* (atoi (substr sw 24 3)) 10)
					)
					(command "_.VIEW" "W" vname (list (- vXcord vdist) (- vYcord vdist)) (list (+ vXcord vdist) (+ vYcord vdist)))
			)
		)
	)
	(setvar "CMDECHO" cmdE)
	(setvar "MAXSORT" maxS)
	(if Bug (princ "\nView4Cadet exited}\n"))
	(princ)
)

(if AppNam
	(if (= (substr (strcase AppNam) 1 5) "ADDSP")
		(C:View4Cadet)
		(setq	LodVer	"1.51a")
	)
	(setq	LodVer	"1.51a")
)

(princ LodVer)
(princ)
