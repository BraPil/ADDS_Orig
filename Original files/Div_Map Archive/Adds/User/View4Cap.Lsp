(if AppNam								; Code Version Indicator
	(princ (strcat "\n" AppNam " View4Cap Loading."))
	(princ "\nAddsPlot View4Cap Loading.")
)

(defun View4Cap	( /	Eset caplist Cnt Ename	; Builds a CAP file, listing number & XY
					capnum capscale cap 	; location, sorts, then builds a view for each cap.
					vXcord vYcord vdist		; format of caplist is vname=8chr, vXcord=7chr, vYcord=8chr, vdist=3chr
					vname cmdE maxS HeadA HeadB HeadC Filt1 Filt2 FiltA FiltB MyKey LNam )
	(if Bug (princ "\n{View4Cap entered\n"))
	(if (= (getvar "UNDOCTL") 0)
		(command "_.UNDO" "N")
		(if (= (getvar "UNDOCTL") 3)
			(command "_.UNDO" "C" "N")
		)
	)
	(setq	cmdE		(getvar "CMDECHO")
			maxS		(getvar "MAXSORT")
			HeadA	(list	(cons -4 "<AND")
							(cons 0 "INSERT")
							(cons -4 "<OR")
							(cons 2 "CAP")
							(cons 2 "A101")
							(cons -4 "OR>")
					)
			HeadB	(list	(cons -4 "AND>"))
	)
	(if (not Bug)
		(setvar "CMDECHO" 0)
		(setvar "CMDECHO" 1)
	)
	(if (and (= "AddsPlot" AppNam) (/= 0 (getvar "tilemode")))
		(command "_.tilemode" 0)
	)
	(if (and (= "AddsPlot" AppNam) (= 1 (getvar "cvport")))
		(command "_.MSpace")
	)
	(setvar "MAXSORT" 32767)
	(if Div
		(if (= Div "W_")
			(if (setq x (ssget "X" (list (cons 8 "????FL*")))) (command "_.ERASE" x ""))	; Gets rid of fill lines
		)
	)
	(cond
		((= (strcase CordFile) "SUB")
			(if (setq MyKey (ValiStrLst CordKey 2))
				(setq	Filt1	(mapcar '(lambda (x) (cons 8 (strcat x "??CK-*"))) MyKey)
						FiltA	(cons (cons -4 "OR>") (reverse Filt1))
						FiltA	(cons (cons -4 "<OR") (reverse FiltA))
						FiltR	(append HeadA FiltA)
						FiltR	(append FiltR HeadB)
						Eset		(ssget "X" FiltR)
				)
				(setq	Eset	(ssget "X"	(list	(cons -4 "<AND")
													(cons 0 "INSERT")
													(cons -4 "<OR")
														(cons 2 "CAP")
														(cons 2 "A101")
													(cons -4 "OR>")
													(cons 8 "????CK-*")
												(cons -4 "AND>")
										)
							)
				)
			)
		)
		((= (strcase CordFile) "FEEDER")
			(if (setq MyKey (ValiStrLst CordKey 3))
				(setq	Filt1	(mapcar '(lambda (x) (cons 8 (strcat x "?CK-*"))) MyKey)
						FiltA	(cons (cons -4 "OR>") (reverse Filt1))
						FiltA	(cons (cons -4 "<OR") (reverse FiltA))
						FiltR	(append HeadA FiltA)
						FiltR	(append FiltR HeadB)
						Eset		(ssget "X" FiltR)
				)
				(setq	Eset	(ssget "X"	(list	(cons -4 "<AND")
													(cons 0 "INSERT")
													(cons -4 "<OR")
														(cons 2 "CAP")
														(cons 2 "A101")
													(cons -4 "OR>")
													(cons 8 "????CK-*")
												(cons -4 "AND>")
										)
							)
				)
			)
		)
		(T
				(setq	Eset	(ssget "X"	(list	(cons -4 "<AND")
													(cons 0 "INSERT")
													(cons -4 "<OR")
														(cons 2 "CAP")
														(cons 2 "A101")
													(cons -4 "OR>")
													(cons 8 "????CK-*")
												(cons -4 "AND>")
										)
							)
				)
		)
	)
	(if Eset
		(progn
			(setq	caplist	(list )
					Cnt		0
					Bubba	(princ (strcat "\nView4Cap is working {" (itoa (sslength Eset)) "} switches..."))
			)
			(if Bug (setq Eds_Eset Eset))
			(while (setq Ename (ssname Eset Cnt))
				(if (= (cdr (assoc 66 (entget Ename))) 1)
					(progn
						(setq	Enext	(entnext Ename)
								capnum	(cdr (assoc 1 (entget Enext)))
								captype	(cdr (assoc 2 (entget Enext)))
								capscale	(cdr (assoc 41 (entget Ename)))
								LNam		(cdr (assoc 8 (entget Ename)))
								Found	nil
						)
						(if (or (= (strcase captype) "CAPACITOR") (= (strcase captype) "LOC_NUM"))
							(if (and Bug LNam capnum)
								(princ (strcat "\n[Bug] Cnt:{" (itoa Cnt) "} Layer:{" LNam "} CapNum:{" capnum "}"))
								(if (and Bug LNam)
									(princ (strcat "\n[Bug] Cnt:{" (itoa Cnt) "} Layer:{" LNam "} CAPACITOR but No capnum?"))
								)
							)
							(while (and (not Found) (/= (cdr (assoc 0 (entget Enext))) "SEQEND"))
								(setq	Enext	(entnext Enext)
										capnum	(cdr (assoc 1 (entget Enext)))
										captype	(cdr (assoc 2 (entget Enext)))
								)
								(if (or (= (strcase captype) "CAPACITOR") (= (strcase captype) "LOC_NUM"))
									(setq	Found	T)
								)
								(if (and Bug LNam capnum)
									(princ (strcat "\n[Bug] Cnt:{" (itoa Cnt) "} Layer:{" LNam "} CapNum:{" capnum "} CapType:{" captype "}"))
									(if (and Bug LNam)
										(princ (strcat "\n[Bug] Cnt:{" (itoa Cnt) "} Layer:{" LNam "} no CAPACITOR and No capnum?"))
									)
								)
							)
						)
						(if (and (>= (strlen capnum) 1) (not (wcmatch capnum "*`,*,* *,*`#*,*.*,LFSP,PDMT,*KVAR")))
							(setq	caplist	(cons	(strcat	(substr (strcat capnum "        ") 1 8)
															(substr (strcat (itoa (fix (cadr (assoc 10 (entget Ename))))) "          ") 1 7)
															(substr (strcat (itoa (fix (caddr(assoc 10 (entget Ename))))) "          ") 1 8)
															(substr (strcat (itoa (fix capscale)) "          ") 1 3)
													)
													caplist
											)
							)
						)
					)
					(progn
						(setq	LNam		(cdr (assoc 8 (entget Ename))))
						(if (and Bug LNam)
							(princ (strcat "\n[Bug] Cnt:{" (itoa Cnt) "} Layer:{" LNam "} No assoc 66?"))
						)
					)
				)
				(if Bug (princ (strcat "[+" (itoa Cnt) "]")))
				(setq	Cnt	(1+ Cnt))
			)
			(if caplist
				(setq	caplist	(acad_strlsort caplist))
			)
			(if (and caplist Bug)
				(setq	eds_caplist	caplist)
			)
			(if caplist
				(foreach	cap
						caplist
						(setq	vname	(rtrim (substr cap 1 8))
								vXcord	(atoi (substr cap 9 7))
								vYcord	(atoi (substr cap 16 8))
								;vdist	(* (atoi (substr cap 24 3)) 10)
								vdist	(if pldname
											(if (= (substr (strcase pldname) 1 3) "ORD")
												(* (atoi (substr cap 24 3)) 2.5)
												(* (atoi (substr cap 24 3)) 10)
											)
											(* (atoi (substr cap 24 3)) 10)
										)
						)
						(command "_.VIEW" "W" vname (list (- vXcord vdist) (- vYcord vdist)) (list (+ vXcord vdist) (+ vYcord vdist)))
				)
			)
		)
	)
	(setvar "CMDECHO" cmdE)
	(setvar "MAXSORT" maxS)
	;	Cleanup
	(if x
		(progn
			(setq x nil)
			(gc)
		)
	)
	(if Eset
		(progn
			(setq x Eset)
			(gc)
		)
	)
	(if Bug (princ "\nView4Cap exited}\n"))
	(princ)
)

(if (= (substr (strcase AppNam) 1 5) "ADDSP")
	(View4Cap)
	(setq	LodVer	"1.50b")
)
(setq	LodVer	"1.50b")
