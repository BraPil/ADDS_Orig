(if AppNam								; Code Version Indicator
	(princ (strcat "\n" AppNam " ThinUG Loading."))
	(princ "\nAddsPlot ThinUG Loading.")
)

(defun ThinUG ( SC /	SS C EntNam NEWWID		; Thins all UG circuits
					flag lacolor la )
	(if (and (= (getvar "tilemode") 0) (= (getvar "cvport") 1))
		(progn
			(setq	flag		T)
			(command "_.mspace")
		)
	)
	(if	(setq	SS	(ssget "X"	(list	(cons -4 "<OR")
											(cons 0 "POLYLINE")
											(cons 0 "LWPOLYLINE")
										(cons -4 "OR>")
										(cons -4 "<OR")
											(cons 8 "???UCK-*")
											(cons 8 "???UFL-*")
										(cons -4 "OR>")
								)
					)
		)
		(progn
			(princ (strcat "\nSizing " (itoa (sslength SS)) " circuits width.....!"))
			(setq	C	0)
			(if (not (tblsearch "LAYER" "UGCKT"))
				(command "_.LAYER" "N" "UGCKT" "")
			)
			(repeat	(sslength SS)
					(setq	EntNam	(ssname SS C)
							NEWWID	(* 0.01 SC)
					)
					(if (/= (cdr (assoc 40 (entget EntNam))) NEWWID)
						(command "_.pedit" EntNam "W" NEWWID "X")
					)
					(setq	la		(cdr (assoc 8 (entget EntNam)))
							lacolor	(cdr (assoc 62 (tblsearch "LAYER" la)))
					)
					(command "_.CHANGE" EntNam "" "P" "LA" "UGCKT" "C" lacolor "")
					(setq	C	(1+ C))
			)
		)
	)
	(if flag
		(command "_.PSPACE")
	)
	(princ)
)

(if (= (substr (strcase AppNam) 1 5) "ADDSP")
	(if (and Sc Symsc)
		(ThinUG (/ (* Sc Symsc) 100.0))
		(princ "\nMissing values for Sc and Symsc")
	)
	(setq	LodVer	"1.50")
)
