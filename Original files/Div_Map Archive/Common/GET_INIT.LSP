(if AppNam								; Code Version Indicator {3240 Lines of Code}
	(princ (strcat "\n" AppNam " Get_Init Loading."))
	(princ "\nCadet 2.2 Get_Init Loading.")
)

(defun SwapApp ( NewApp /	IsGood )			; Should swap the current application...
	(if (and GetProf (member NewApp (list "CADET" "BEMS" "ADDS")))
		(if DevMark
			(cond
				((= NewApp "CADET")
					(setq	S::StartUp	nil)
					(setq	IsGood	(GetProf "CADET20_T"))
					(if IsGood
						(progn
							(load "S:\\Workgroups\\APC Power Delivery\\Division Mapping Test\\Cadet20\\MENU\\Cadet20_T.mnl")
							(CadetGo)
							(FreshDwg)
						)
					)
				)
				((= NewApp "ADDS")
					(setq	S::StartUp	nil)
					(setq	IsGood	(GetProf "ADDS_T"))
					(if IsGood
						(progn
							(load "S:\\Workgroups\\APC Power Delivery\\Division Mapping Test\\ADDS\\MENU\\ADDS_T.mnl")
							(AddsGo)
							(FreshDwg)
						)
					)
				)
			)
			(cond
				((= NewApp "CADET")
					(setq	S::StartUp	nil)
					(setq	IsGood	(GetProf "CADET20"))
					(if IsGood
						(progn
							(load "S:\\Workgroups\\APC Power Delivery\\Division Mapping\\Cadet20\\MENU\\Cadet20.mnl")
							(CadetGo)
							(FreshDwg)
						)
					)
				)
				((= NewApp "ADDS")
					(setq	S::StartUp	nil)
					(setq	IsGood	(GetProf "ADDS"))
					(if IsGood
						(progn
							(load "S:\\Workgroups\\APC Power Delivery\\Division Mapping\\ADDS\\MENU\\ADDS.mnl")
							(AddsGo)
							(FreshDwg)
						)
					)
				)
			)
		)
	)
)

(defun Find_INI ( /	Pth_INI _Path-INI		; Finds INI file and returns path
					Old_Drv Old_Dir )
	(if Bug (princ "\nLocating INI file, please wait..."))
	(if Bug (Twaddle 0 20))
	
	(setq	Pth_INI	(list (findfile "C:\\DIV_MAP\\DIV_MAP.INI")))
	
	(if Pth_INI
		(setq	_Path-Person	(dos_splitpath (car Pth_INI)))
		(cond														;If the INI file is not found
			((member "C:" (dos_drives))
				(if Bug (princ "\nLocating INI file version not 3 or 4"))
				(setq	_Path-Person	"C:")
				(if (member "DIV_MAP" (mapcar (quote strcase) (dos_subdir _Path-Person)))
					(setq	_Path-Person	(strcat _Path-Person "\\DIV_MAP\\"))
					(progn
						(if (/= (dos_drive) "C:")
							(setq	Old_Drv	(dos_drive)
									Bubba	(dos_drive "C:")
							)
							(setq	Old_Drv	nil)
						)
						(if (/= (dos_pwdir) "C:\\")
							(setq	Old_Dir	(dos_pwdir)
									Bubba	(dos_chdir "C:\\")
							)
							(setq	Old_Dir	nil)
						)
						(dos_mkdir "\\DIV_MAP")
						(setq	_Path-Person	(strcat _Path-Person "\\DIV_MAP\\"))
						(if Old_Dir
							(setq	Bubba	(dos_chdir Old_Dir))
						)
						(if Old_Drv
							(setq	Bubba	(dos_drive Old_Drv))
						)
					)
				)
			)
		)
	)
	(if Bug (Twaddle 20 20))
	(if _Path-Person
		(if Pth_INI
			(setq	_Path-INI		(car Pth_INI)
					_Path-Person	(strcat (nth 0 _Path-Person) (nth 1 _Path-Person))
			)
			(setq	_Path-INI		nil)
		)
		(setq	_Path-INI		nil)
	)
	(if Bug (Twaddle -40 40))
	_Path-INI
)

(defun Init_INI ( / Fnam Bubba PthLst Gen_User )	; Initializes INI file Paths
	(setq	Fnam	(Find_INI))
	(if (and Fnam AppNam)
		(if (dos_getini (StpDot AppNam) "SndPick01Test" Fnam)
			(if (not (equal (dos_getini (StpDot AppNam) "SndPick01Test" Fnam) "default"))
				(setq	SndPick01	(atoi (dos_getini (StpDot AppNam) "SndPick01Val" Fnam)))
				(ResetSPick01 Fnam)
			)
			(ResetSPick01 Fnam)
		)
		(princ "\nSkipping Sound Personalization 1...\n")
	)
	(if (and Fnam AppNam)
		(if (dos_getini (StpDot AppNam) "SndPick02Test" Fnam)
			(if (not (equal (dos_getini (StpDot AppNam) "SndPick02Test" Fnam) "default"))
				(setq	SndPick02	(atoi (dos_getini (StpDot AppNam) "SndPick02Val" Fnam)))
				(ResetSPick02 Fnam)
			)
			(ResetSPick02 Fnam)
		)
		(princ "\nSkipping Sound Personalization 2...\n")
	)
	(cond
		((and Fnam (= (StpDot AppNam) "ADDS"));==================== ADDS Loader - INI file found ====================
			(setq	Adds_User			(dos_getini (StpDot AppNam) "UserName" Fnam)
					AppDwtNam			(dos_getini (StpDot AppNam) "DwtNam" Fnam)
					AppDbNam			(dos_getini (StpDot AppNam) "Server" Fnam)
					_Path-DLG			(dos_getini (StpDot AppNam) "DLG" Fnam)
					_Path-DWF			(dos_getini (StpDot AppNam) "DWF" Fnam)
					_Path-DWG			(dos_getini (StpDot AppNam) "Dwg" Fnam)
					_Path-LUT			(dos_getini (StpDot AppNam) "LUT" Fnam)
					_Path-Lisp		(dos_getini (StpDot AppNam) "Lisp" Fnam)
					_Path-Menu		(dos_getini (StpDot AppNam) "Menu" Fnam)
					_Path-Person		(dos_getini (StpDot AppNam) "Person" Fnam)
					_Path-Plot		(dos_getini (StpDot AppNam) "Plot" Fnam)
					_Path-Quad		(dos_getini (StpDot AppNam) "DLG" Fnam)
					_Path-Sym			(dos_getini (StpDot AppNam) "Sym" Fnam)
					_Path-User		(dos_getini (StpDot AppNam) "UserP" Fnam)
					TMult			(dos_getini (StpDot AppNam) "TMULT" Fnam)
					SMult			(dos_getini (StpDot AppNam) "SMULT" Fnam)
					_Alt_Path-Panel	(strcat PrmRootPath "Shared Panels\\")
					_Warning_Size		(dos_getini (StpDot AppNam) "WarnSize" Fnam)
			)
			; Checks to see if multplier setting are strings convert them to Floats else call for dialog box to set multpliers.
			(if (and (= (type SMult) (quote STR)) (= (type TMult) (quote STR)))
				(if (and (> (strlen SMult) 1) (> (strlen TMult) 1))
					(setq	SMult	(/ (float (atoi SMult)) 100.0)
							TMult	(/ (float (atoi TMult)) 100.0)
					)
					(MultDlg nil nil)
				)
				(MultDlg nil nil)
			)
			(if Bug (Twaddle 97 100))
			
			;	If any var not set call Upd_INI 
			(if	(not	(and	_Path-Sym _Path-Menu _Path-LUT _Path-Lisp _Path-User
						_Path-Dwg _Path-Person ; Adds_HD Adds_Net Adds_Old
						Adds_User _Path-Plot _Path-DLG _Path-DWF
					)
				)
				(Upd_INI)
			)
			(if Bug (Twaddle 98 100))
			(if Adds_User
				(setq	Gen_User	Adds_User)
			)
			(if Bug (Twaddle 98 100))
			(if Bug (Twaddle 99 100))
			(if Bug (Twaddle 100 100))
			(if Bug (Twaddle -10 100))
		)
		((= (StpDot AppNam) "ADDS")	;==================== ADDS30 Loader - INI file NOT found ====================
			(setq	Fnam				(strcat _Path-Person "DIV_MAP.INI")
					PthLst			(PathDlg)
					_Alt_Path-Panel	(strcat PrmRootPath "Shared Panels\\")
			)
			(if (not (and SMult TMult))
				(MultDlg nil nil)
			)
			(if Bug (princ (strcat "\nInit_INI (" AppNam ") about to dos_setini with " Fnam "\n")))
			(if Adds_User
				(dos_setini (StpDot AppNam) "UserName" Adds_User Fnam)
				(if Bug (princ "\nAdds_User not defined!"))
			)
			(if AppDwtNam
				(dos_setini (StpDot AppNam) "DwtNam" AppDwtNam Fnam)
				(if Bug (princ "\nAdds_User not defined!"))
			)
			(if AppDbNam
				(dos_setini (StpDot AppNam) "Server" AppDbNam Fnam)
				(if Bug (princ "\nAdds_User not defined!"))
			)
			(if _Path-Person
				(dos_setini (StpDot AppNam) "Person" _Path-Person Fnam)
				(if Bug (princ "\nPath-Person not defined!"))
			)
			(if _Path-Dwg
				(dos_setini (StpDot AppNam) "Dwg" _Path-Dwg Fnam)
				(if Bug (princ "\nPath-DWG not defined!"))
			)
			(if _Path-Plot
				(dos_setini (StpDot AppNam) "Plot" _Path-Plot Fnam)
				(if Bug (princ "\nPath-Plot not defined!"))
			)
			(if _Path-User
				(dos_setini (StpDot AppNam) "UserP" _Path-User Fnam)
				(if Bug (princ "\nPath-User not defined!"))
			)
			(if _Path-Lisp
				(dos_setini (StpDot AppNam) "Lisp" _Path-Lisp Fnam)
				(if Bug (princ "\nPath-Lisp not defined!"))
			)
			(if _Path-LUT
				(dos_setini (StpDot AppNam) "LUT" _Path-LUT Fnam)
				(if Bug (princ "\nPath-LUT not defined!"))
			)
			(if _Path-Menu
				(dos_setini (StpDot AppNam) "Menu" _Path-Menu Fnam)
				(if Bug (princ "\nPath-Menu not defined!"))
			)
			(if _Path-Sym
				(dos_setini (StpDot AppNam) "Sym" _Path-Sym Fnam)
				(if Bug (princ "\nPath-Sym not defined!"))
			)
			(if _Path-DLG
				(dos_setini (StpDot AppNam) "DLG" _Path-DLG Fnam)
				(if Bug (princ "\nPath-DLG not defined!"))
			)
			(if _Path-DWF
				(dos_setini (StpDot AppNam) "DWF" _Path-DWF Fnam)
				(if Bug (princ "\nPath-DWF not defined!"))
			)
			(if TMult
				(dos_setini (StpDot AppNam) "TMult" (rtos (* 100.0 TMult) 2 0) Fnam)
				(if Bug (princ "\nTMult not defined!"))
			)
			(if SMult
				(dos_setini (StpDot AppNam) "SMult" (rtos (* 100.0 SMult) 2 0) Fnam)
				(if Bug (princ "\nSMult not defined!"))
			)
			(if Adds_User
				(setq	Gen_User	Adds_User)
			)
		)
		
		((and Fnam (= (StpDot AppNam) "ADDSPLOT"))										;==================== ADDSPLOT Loader - INI file found ====================
			(setq	Adds_User		(dos_getini (StpDot AppNam) "UserName" Fnam)
					AppDwtNam		(dos_getini (StpDot AppNam) "DwtNam" Fnam)
					AppDbNam		(dos_getini (StpDot AppNam) "Server" Fnam)
					_Path-DLG		(dos_getini (StpDot AppNam) "DLG" Fnam)
					_Path-DWF		(dos_getini (StpDot AppNam) "DWF" Fnam)
					_Path-DWG		(dos_getini (StpDot AppNam) "Dwg" Fnam)
					_Path-LUT		(dos_getini (StpDot AppNam) "LUT" Fnam)
					_Path-Lisp	(dos_getini (StpDot AppNam) "Lisp" Fnam)
					_Path-Menu	(dos_getini (StpDot AppNam) "Menu" Fnam)
					_Path-Person	(dos_getini (StpDot AppNam) "Person" Fnam)
					_Path-Plot	(dos_getini (StpDot AppNam) "Plot" Fnam)
					_Path-Quad	(dos_getini (StpDot AppNam) "DLG" Fnam)
					_Path-Sym		(dos_getini (StpDot AppNam) "Sym" Fnam)
					_Path-User	(dos_getini (StpDot AppNam) "UserP" Fnam)
					_Alt_Path-Panel	(strcat PrmRootPath "Shared Panels\\")
					TMult		(dos_getini (StpDot AppNam) "TMULT" Fnam)
					SMult		(dos_getini (StpDot AppNam) "SMULT" Fnam)
			)
			(if (and (= (type SMult) 'STR) (= (type TMult) 'STR))
				(if (and (> (strlen SMult) 1) (> (strlen TMult) 1))
					(setq	SMult	(/ (float (atoi SMult)) 100.0)
							TMult	(/ (float (atoi TMult)) 100.0)
					)
					(MultDlg nil nil)
				)
				(MultDlg nil nil)
			)
			(if	(or	(not	(and	_Path-Sym _Path-Menu _Path-LUT _Path-Lisp _Path-User
							_Path-Dwg _Path-Person AppDwtNam
							Adds_User _Path-Plot _Path-DLG _Path-DWF
						)
					)
					(= _Path-Lisp "default")
				)
				(Upd_INI)
			)
			(if Adds_User
				(setq	Gen_User	Adds_User)
			)
		)
		((= (StpDot AppNam) "ADDSPLOT")												;==================== ADDSPLOT Loader - INI file NOT found ====================
			(setq	Fnam		(strcat _Path-Person "DIV_MAP.INI")
					PthLst	(PathDlg)
			)
			(if (not (and SMult TMult))
				(MultDlg nil nil)
			)
			(if PthLst
				(setq	Bubba	(dos_setini "ADDSPLOT" "UserName" Adds_User Fnam)
						Bubba	(dos_setini "ADDSPLOT" "Person" _Path-Person Fnam)
						Bubba	(dos_setini "ADDSPLOT" "Dwg" _Path-Dwg Fnam)
						Bubba	(dos_setini "ADDSPLOT" "Plot" _Path-Plot Fnam)
						Bubba	(dos_setini "ADDSPLOT" "UserP" _Path-User Fnam)
						Bubba	(dos_setini "ADDSPLOT" "Lisp" _Path-Lisp Fnam)
						Bubba	(dos_setini "ADDSPLOT" "LUT" _Path-LUT Fnam)
						Bubba	(dos_setini "ADDSPLOT" "Menu" _Path-Menu Fnam)
						Bubba	(dos_setini "ADDSPLOT" "Sym" _Path-Sym Fnam)
						Bubba	(dos_setini "ADDSPLOT" "DLG" _Path-DLG Fnam)
						Bubba	(dos_setini "ADDSPLOT" "DWF" _Path-DWF Fnam)
						Bubba	(dos_setini "ADDSPLOT" "TMult" (rtos (* 100.0 TMult) 2 0) MultINI)
						Bubba	(dos_setini "ADDSPLOT" "SMult" (rtos (* 100.0 SMult) 2 0) MultINI)
				)
			)
			(if Adds_User
				(setq	Gen_User	Adds_User)
			)
		)
		((and Fnam (or (wcmatch (StpDot AppNam) "CADET##")(=(StpDot AppNam) "CADET")))			;==================== CADET Loader - INI file found ====================
			(setq	Cadet_User		(dos_getini (StpDot AppNam) "UserName" Fnam)
					Cadet_Old			(dos_getini (StpDot AppNam) "Old" Fnam)
					Cadet_Net			(dos_getini (StpDot AppNam) "Net" Fnam)
					Cadet_HD			(dos_getini (StpDot AppNam) "HD" Fnam)
					AppDwtNam			(dos_getini (StpDot AppNam) "DwtNam" Fnam)
					_Path-Person		(dos_getini (StpDot AppNam) "Person" Fnam)
					_Path-DLG			(dos_getini (StpDot AppNam) "DLG" Fnam)
					_Path-Dwg			(dos_getini (StpDot AppNam) "Dwg" Fnam)
					_Path-Plot		(dos_getini (StpDot AppNam) "Plot" Fnam)
					_Path-Quad		(dos_getini (StpDot AppNam) "DLG" Fnam)
					_Path-User		(dos_getini (StpDot AppNam) "UserP" Fnam)
					_Path-Lisp		(dos_getini (StpDot AppNam) "Lisp" Fnam)
					_Path-LUT			(dos_getini (StpDot AppNam) "LUT" Fnam)
					_Path-Menu		(dos_getini (StpDot AppNam) "Menu" Fnam)
					_Path-Sym			(dos_getini (StpDot AppNam) "Sym" Fnam)
					_Alt_Path-Panel	(strcat PrmRootPath "Shared Panels\\")
			)
			(if	(not	(and	_Path-Sym _Path-Menu _Path-LUT _Path-Lisp _Path-User
						_Path-Dwg _Path-Person Cadet_HD Cadet_Net
						Cadet_User _Path-Plot Cadet_Old
					)
				)
				(Upd_INI)
			)
			(if Cadet_User
				(setq	Gen_User	Cadet_User)
			)
		)
		((or (wcmatch (StpDot AppNam) "CADET##")(=(StpDot AppNam) "CADET"))					;==================== CADET Loader - INI file NOT found ====================
			(setq	Fnam		(strcat _Path-Person "DIV_MAP.INI")
					PthLst	(PathDlg)
			)
			(if Bug (princ (strcat "\nInit_INI (" AppNam ") about to dos_setini with " Fnam "\n")))
			(if Cadet_User
				(dos_setini (StpDot AppNam) "UserName" Cadet_User Fnam)
				(if Bug (princ "\nCadet_User not defined!"))
			)
			(if Cadet_Old
				(dos_setini (StpDot AppNam) "Old" Cadet_Old Fnam)
				(if Bug (princ "\nCadet_Old not defined!"))
			)
			(if Cadet_Net
				(dos_setini (StpDot AppNam) "Net" Cadet_Net Fnam)
				(if Bug (princ "\nCadet_Net not defined!"))
			)
			(if Cadet_HD
				(dos_setini (StpDot AppNam) "HD" Cadet_HD Fnam)
				(if Bug (princ "\nCadet_HD not defined!"))
			)
			(if _Path-Person
				(dos_setini (StpDot AppNam) "Person" _Path-Person Fnam)
				(if Bug (princ "\nPath-Person not defined!"))
			)
			(if _Path-Dwg
				(dos_setini (StpDot AppNam) "Dwg" _Path-Dwg Fnam)
				(if Bug (princ "\nPath-Dwg not defined!"))
			)
			(if _Path-Plot
				(dos_setini (StpDot AppNam) "Plot" _Path-Plot Fnam)
				(if Bug (princ "\nPath-Plot not defined!"))
			)
			(if _Path-User
				(dos_setini (StpDot AppNam) "UserP" _Path-User Fnam)
				(if Bug (princ "\nPath-User not defined!"))
			)
			(if _Path-Lisp
				(dos_setini (StpDot AppNam) "Lisp" _Path-Lisp Fnam)
				(if Bug (princ "\nPath-Lisp not defined!"))
			)
			(if _Path-LUT
				(dos_setini (StpDot AppNam) "LUT" _Path-LUT Fnam)
				(if Bug (princ "\nPath-LUT not defined!"))
			)
			(if _Path-Menu
				(dos_setini (StpDot AppNam) "Menu" _Path-Menu Fnam)
				(if Bug (princ "\nPath-Menu not defined!"))
			)
			(if _Path-Sym
				(dos_setini (StpDot AppNam) "Sym" _Path-Sym Fnam)
				(if Bug (princ "\nPath-Sym not defined!"))
			)
			(if Cadet_User
				(setq	Gen_User	Cadet_User)
			)
		)
		;==================== SUBTOOLS Loader - INI file found ====================
		((and Fnam (= (StpDot AppNam) "SUBTOOLS"))
			(setq	SubT_User			(dos_getini (StpDot AppNam) "UserName" Fnam)
					AppDwtNam			(dos_getini (StpDot AppNam) "DwtNam" Fnam)
					AppDbNam			(dos_getini (StpDot AppNam) "Server" Fnam)
					_Path-Person		(dos_getini (StpDot AppNam) "Person" Fnam)
					_Path-DWG			(dos_getini (StpDot AppNam) "Dwg" Fnam)
					_Path-Plot		(dos_getini (StpDot AppNam) "Plot" Fnam)
					_Path-User		(strcat PrmRootPath "ADDS\\User\\")
					_Path-Lisp		(dos_getini (StpDot AppNam) "Lisp" Fnam)
					_Path-LUT			(dos_getini (StpDot AppNam) "LUT" Fnam)
					_Path-Menu		(dos_getini (StpDot AppNam) "Menu" Fnam)
					_Path-Sym			(dos_getini (StpDot AppNam) "Sym" Fnam)
					_Path-DLG			(dos_getini (StpDot AppNam) "DLG" Fnam)
					_Path-DWF			(dos_getini (StpDot AppNam) "DWF" Fnam)
					_Alt_Path-Panel	(strcat PrmRootPath "Shared Panels\\")
			)
			(if	(or	(not	(and	SubT_User
							_Path-Person
							_Path-Dwg
							_Path-Plot
							_Path-User
							_Path-Lisp
							_Path-LUT
							_Path-Menu
							_Path-Sym
							_Path-DLG
							_Path-DWF
						)
					)
					(= _Path-Lisp "default")
				)
				(Upd_INI)
			)
			(if SubT_User
				(setq	Gen_User	SubT_User)
			)
		)
	)
	(if DevMark
		(cond
			((= (StpDot AppNam) "ADDS")
				(setq	_Path-Lisp		(strcat TestPrmRootPath "ADDS\\Lisp\\")
						_Path-LUT			(strcat TestPrmRootPath "ADDS\\LUT\\")
						_Path-Menu		(strcat TestPrmRootPath "ADDS\\Menu\\")
						_Path-Sym			(strcat TestPrmRootPath "ADDS\\Sym\\")
						_Path-DLG			(strcat TestPrmRootPath "Quad\\")
						_Alt_Path-Panel	(strcat TestPrmRootPath "DivData\\Shared Panels\\")
						
				)
			)
			((= (StpDot AppNam) "ADDSPLOT")
				(if Fnam
					(setq 	_Path-User	(dos_getini (StpDot AppNam) "UserP" Fnam)
							_Path-Lisp	(dos_getini (StpDot AppNam) "Lisp" Fnam)
							_Path-LUT		(dos_getini (StpDot AppNam) "LUT" Fnam)
							_Path-Menu	(dos_getini (StpDot AppNam) "Menu" Fnam)
							_Path-Sym		(dos_getini (StpDot AppNam) "Sym" Fnam)
							_Path-DLG		(dos_getini (StpDot AppNam) "DLG" Fnam)
					)
				)
			)
			((= (StpDot AppNam) "SUBTOOLS")
				(setq	_Path-Lisp		(strcat TestPrmRootPath "SubTools\\Lisp\\")
						_Path-LUT			(strcat TestPrmRootPath "LookUpTable\\")
						_Path-Menu		(strcat TestPrmRootPath "SubTools\\Menu\\")
						_Path-User		(strcat TestPrmRootPath "ADDS\\User\\")
						_Path-Sym			(strcat TestPrmRootPath "\SubTools\\Sym\\")
						_Path-DLG			(strcat TestPrmRootPath "Quad\\")
						_Alt_Path-Panel	(strcat TestPrmRootPath "DivData\\Shared Panels\\")
				)
			)
			((wcmatch (StpDot AppNam) "ADDS##")
				(setq	_Path-Lisp		(strcat TestPrmRootPath "Adds30\\Lisp\\")
						_Path-LUT			(strcat TestPrmRootPath "Adds30\\LUT\\")
						_Path-Menu		(strcat TestPrmRootPath "Adds30\\Menu\\")
						_Path-Sym			(strcat TestPrmRootPath "Adds30\\Sym\\")
						_Path-DLG			(strcat TestPrmRootPath "Quad\\")
						_Alt_Path-Panel	(strcat TestPrmRootPath "DivData\\Shared Panels\\")
				)
			)
		)
	)
	(if	(and	DevMark
			Div
			(or	(= (StpDot AppNam) "ADDS")
				(= (StpDot AppNam) "ADDSPLOT")
				(= (StpDot AppNam) "BEMS")
				(wcmatch (StpDot AppNam) "CADET##")
				(= (StpDot AppNam) "SUBTOOLS")
				(wcmatch (StpDot AppNam) "ADDS##")
			)
		)
		(DivDevGet Div)
	)
)

(defun Upd_INI ( / Fnam Bubba PthLst )			; Updates INI file paths
	(if Bug (princ "\nGet_Init.Lsp!Upd_Ini - Entered\n"))
	(setq	Fnam	(Find_INI))
	(if (and Bug Fnam)
		(princ (strcat "\nINI file: " Fnam))
	)
	(if (and Bug _Path-Person)
		(princ (strcat "\nPersonal Dir: " _Path-Person))
	)
	(if Fnam
		(setq	PthLst	(PathDlg))
		(if _Path-Person
			(setq	Fnam		(strcat _Path-Person "DIV_MAP.INI")
					PthLst	(PathDlg)
			)
			(setq	PthLst	nil)
		)
	)
	(if (and Bug _Path-Person)
		(princ (strcat "\nPersonal Dir: " _Path-Person))
	)
	(cond
		((and PthLst (= (StpDot AppNam) "ADDSPLOT") (not DevMark))
			(setq    	Bubba	(dos_setini "ADDSPLOT" "UserName" Adds_User Fnam)
					Bubba	(dos_setini "ADDSPLOT" "Person" _Path-Person Fnam)
					Bubba	(dos_setini "ADDSPLOT" "HD" Adds_HD Fnam)
					Bubba	(dos_setini "ADDSPLOT" "DwtNam" AppDwtNam Fnam)
					Bubba	(dos_setini "ADDSPLOT" "Dwg" _Path-Dwg Fnam)
					Bubba	(dos_setini "ADDSPLOT" "DWF" _Path-DWF Fnam)
					Bubba	(dos_setini "ADDSPLOT" "Plot" _Path-Plot Fnam)
					Bubba	(dos_setini "ADDSPLOT" "UserP" _Path-User Fnam)
					Bubba	(dos_setini "ADDSPLOT" "Lisp" _Path-Lisp Fnam)
					Bubba	(dos_setini "ADDSPLOT" "LUT" _Path-LUT Fnam)
					Bubba	(dos_setini "ADDSPLOT" "Menu" _Path-Menu Fnam)
					Bubba	(dos_setini "ADDSPLOT" "Sym" _Path-Sym Fnam)
					Bubba	(dos_setini "ADDSPLOT" "DLG" _Path-DLG Fnam)
			)
		)
		
		((and PthLst (or (= (StpDot AppNam) "ADDS")(= (StpDot AppNam) "ADDS")) (not DevMark))
			(if Bug (princ (strcat "\nUpd_INI (" AppNam ") about to dos_setini with " Fnam "\n")))
			
			(if TMult
				(dos_setini (StpDot AppNam) "TMult" (rtos (* 100.0 TMult) 2 0) Fnam)
				(if Bug (princ "\nTMult not defined!"))
			)
			(if SMult
				(dos_setini (StpDot AppNam) "SMult" (rtos (* 100.0 SMult) 2 0) Fnam)
				(if Bug (princ "\nSMult not defined!"))
			)
			
			;	Server
			
			(if Adds_User
				(dos_setini (StpDot AppNam) "UserName" Adds_User Fnam)
				(if Bug (princ "\nAdds_User not defined!"))
			)
			(if _Path-Person
				(dos_setini (StpDot AppNam) "Person" _Path-Person Fnam)
				(if Bug (princ "\nPath-Person not defined!"))
			)
			
			; 	DwtNam - not in ADDS
			(if (and AppDwtNam (= (StpDot AppNam) "ADDS"))
				(dos_setini (StpDot AppNam) "DwtNam" AppDwtNam Fnam)
				(if Bug (princ "\nAppDwtNam not defined!"))
			)
			(if _Path-Dwg
				(dos_setini (StpDot AppNam) "Dwg" _Path-Dwg Fnam)
				(if Bug (princ "\nPath-DWG not defined!"))
			)
			(if _Path-DWF
				(dos_setini (StpDot AppNam) "DWF" _Path-DWF Fnam)
				(if Bug (princ "\nPath-DWF not defined!"))
			)
			(if _Path-User
				(dos_setini (StpDot AppNam) "UserP" _Path-User Fnam)
				(if Bug (princ "\nPath-User not defined!"))
			)
			(if _Path-Plot
				(dos_setini (StpDot AppNam) "Plot" _Path-Plot Fnam)
				(if Bug (princ "\nPath-Plot not defined!"))
			)
			
			;	Support - not in Adds
			
			(if _Path-Lisp
				(dos_setini (StpDot AppNam) "Lisp" _Path-Lisp Fnam)
				(if Bug (princ "\nPath-Lisp not defined!"))
			)
			(if _Path-LUT
				(dos_setini (StpDot AppNam) "LUT" _Path-LUT Fnam)
				(if Bug (princ "\nPath-LUT not defined!"))
			)
			(if _Path-Menu
				(dos_setini (StpDot AppNam) "Menu" _Path-Menu Fnam)
				(if Bug (princ "\nPath-Menu not defined!"))
			)
			(if _Path-Sym
				(dos_setini (StpDot AppNam) "Sym" _Path-Sym Fnam)
				(if Bug (princ "\nPath-Sym not defined!"))
			)
			(if _Path-DLG
				(dos_setini (StpDot AppNam) "DLG" _Path-DLG Fnam)
				(if Bug (princ "\nPath-DLG not defined!"))
			)
			
			;	Used in CADET not in Adds
;			(if Adds_Old
;				(dos_setini (StpDot AppNam) "Old" Adds_Old Fnam)
;				(if Bug (princ "\nAdds_Old not defined!"))
;			)
;			(if Adds_Net
;				(dos_setini (StpDot AppNam) "Net" Adds_Net Fnam)
;				(if Bug (princ "\nAdds_Net not defined!"))
;			)
;			(if Adds_HD
;				(dos_setini (StpDot AppNam) "HD" Adds_HD Fnam)	; Old AddsPlot, BEMS
;				(if Bug (princ "\nAdds_HD not defined!"))
;			)

		)
		((and PthLst (or (wcmatch (StpDot AppNam) "CADET##")(=(StpDot AppNam) "CADET")) (not DevMark))
			(if Bug (princ (strcat "\nUpd_INI (" AppNam ") about to dos_setini with " Fnam "\n")))
			(if Cadet_User
				(dos_setini (StpDot AppNam) "UserName" Cadet_User Fnam)
				(if Bug (princ "\nCadet_User not defined!"))
			)
			(if Cadet_Old
				(dos_setini (StpDot AppNam) "Old" Cadet_Old Fnam)
				(if Bug (princ "\nCadet_Old not defined!"))
			)
			(if Cadet_Net
				(dos_setini (StpDot AppNam) "Net" Cadet_Net Fnam)
				(if Bug (princ "\nCadet_Net not defined!"))
			)
			(if Cadet_HD
				(dos_setini (StpDot AppNam) "HD" Cadet_HD Fnam)
				(if Bug (princ "\nCadet_HD not defined!"))
			)
			(if _Path-Person
				(dos_setini (StpDot AppNam) "Person" _Path-Person Fnam)
				(if Bug (princ "\nPath-Person not defined!"))
			)
			(if _Path-Dwg
				(dos_setini (StpDot AppNam) "Dwg" _Path-Dwg Fnam)
				(if Bug (princ "\nPath-Dwg not defined!"))
			)
			(if _Path-Plot
				(dos_setini (StpDot AppNam) "Plot" _Path-Plot Fnam)
				(if Bug (princ "\nPath-Plot not defined!"))
			)
			(if _Path-User
				(dos_setini (StpDot AppNam) "UserP" _Path-User Fnam)
				(if Bug (princ "\nPath-User not defined!"))
			)
			(if _Path-Lisp
				(dos_setini (StpDot AppNam) "Lisp" _Path-Lisp Fnam)
				(if Bug (princ "\nPath-Lisp not defined!"))
			)
			(if _Path-LUT
				(dos_setini (StpDot AppNam) "LUT" _Path-LUT Fnam)
				(if Bug (princ "\nPath-LUT not defined!"))
			)
			(if _Path-Menu
				(dos_setini (StpDot AppNam) "Menu" _Path-Menu Fnam)
				(if Bug (princ "\nPath-Menu not defined!"))
			)
			(if _Path-Sym
				(dos_setini (StpDot AppNam) "Sym" _Path-Sym Fnam)
				(if Bug (princ "\nPath-Sym not defined!"))
			)
			(tables)
		)
	)
	(if Bug (princ "\nGet_Init.Lsp!Upd_Ini - Done\n"))
	(princ)
)

(defun Upd_Mlt ( / )
	(setq	Fnam	(Find_INI))
	(if (and Bug Fnam)
		(princ (strcat "\nINI file: " Fnam))
	)
	(if Fnam 
		(MultDlg TMult SMult)
	)

)

(defun MultDlg ( M1 M2 /	dlg				; Big INI Path set function
						Dcl_Pan M1_Lst M2_Lst )
	(setq	dlg		2)
	(if M1
		(setq	M1_Lst	(rtos (* 100.0 M1) 2 0))
		(setq	M1_Lst	"100")
	)
	(if M2
		(setq	M2_Lst	(rtos (* 100.0 M2) 2 0))
		(setq	M2_Lst	"100")
	)
	(if (setq Dcl_Pan (findfile "Get_Init.dcl"))
		(if (> (setq Dcl_Pan (load_dialog Dcl_Pan)) 0)
			(while (> dlg 1)
				(new_dialog "INIMult" Dcl_Pan)
				(set_tile "TM_EDIT" (strcat M1_Lst "%"))
				(set_tile "TM_SLDR" M1_Lst)
				(set_tile "SM_EDIT" (strcat M2_Lst "%"))
				(set_tile "SM_SLDR" M2_Lst)
				(if (and M1_Lst Bug) (princ (strcat "\nTMult set to: " M1_Lst)))
				(if (and M2_Lst Bug) (princ (strcat "\nSMult set to: " M2_Lst)))
				(action_tile "TM_SLDR" "(setq M1_Lst $value)(set_tile \"TM_EDIT\" (strcat $value (chr 37)))")
				(action_tile "TM_EDIT" "(setq M1_Lst $value)(set_tile \"TM_SLDR\" (if (= (substr $value 1 4) (chr 37)) (substr $value 1 3) $value))")
				(action_tile "SM_SLDR" "(setq M2_Lst $value)(set_tile \"SM_EDIT\" (strcat $value (chr 37)))")
				(action_tile "SM_EDIT" "(setq M2_Lst $value)(set_tile \"SM_SLDR\" (if (= (substr $value 1 4) (chr 37)) (substr $value 1 3) $value))")
				(action_tile "ok_button" "(done_dialog 1)")
				(action_tile "cancel_button" "(done_dialog 0)")
				(setq dlg (start_dialog))
				(unload_dialog Dcl_Pan)
			)
			(alert "\nUnable to open DCL file")
		)
		(alert "\nUnable to find DCL file")
	)
	(if (> dlg 0)
		(progn
			(if M1_Lst (setq TMult (/ (float (atoi M1_Lst)) 100.0)))
			(if (and M1_Lst Bug)
				(princ (strcat "\nTMult set to: " M1_Lst))
			)
			(if M2_Lst (setq SMult (/ (float (atoi M2_Lst)) 100.0)))
			(if (and M2_Lst Bug)
				(princ (strcat "\nSMult set to: " M2_Lst))
			)
			(if _Path-Person
				(setq	MultINI	(strcat _Path-Person "DIV_MAP.INI"))
				(setq	MultINI	(Find_INI))
			)
			(cond 
				((and (= (StpDot AppNam) "ADDS")	(not DevMark))			
					(setq	AppKey 	"ADDS")
				)
				((and (= (StpDot AppNam) "ADDSPLOT") (not DevMark))
					(setq	AppKey 	"ADDSPLOT")
				)
			)
			(setq	Bubba	(dos_setini AppKey "TMult" (rtos (* 100.0 TMult) 2 0) MultINI)
					Bubba	(dos_setini AppKey "SMult" (rtos (* 100.0 SMult) 2 0) MultINI)
			)
		)
	)
	(princ)
)

(defun PathDlg ( /	dlg Cnt HdVal NdVal NamVal	; INI Path Dialog
				DrLst Dcl_Pan ActLst GoPath DosLibVer )	;;;	CET 07/26/2007 Added DosLib

;;;	CET 07/26/2007 Added Select to handle AutoCAD 2007 place before Application name check because same basic code block
;;; 			was repeated for each application.

;;;	Check and load correct version of Dos Library functions if need.
	(cond 
		((= (substr (getvar "ACADVER") 1 4) "24.2")	;	AutoCAD 2023
			(setq DosLibVer "DOSLib24x64.arx")
		)
		((= (substr (getvar "ACADVER") 1 4) "23.0")	;	AutoCAD 2019
			(setq DosLibVer "DOSLib23x64.arx")
		)
		((= (substr (getvar "ACADVER") 1 4) "20.1")	;	AutoCAD 2016
			(setq DosLibVer "DOSLib20x64.arx")
		)
		((= (substr (getvar "ACADVER") 1 4) "18.2")	;	AutoCAD 2012
			(setq DosLibVer "DosLib18x64.arx")
		)
		((= (substr (getvar "ACADVER") 1 4) "17.0")	;	AutoCAD 2007
			(setq DosLibVer "doslib17.arx")
		)
		((= (getvar "ACADVER") "15.0")			;	AutoCAD 2000
			(setq DosLibVer "doslib2k.arx")
		)
		(T
			(setq DosLibVer "doslib14.arx")
		)
	)
 	(if DosLibVer
		(if (not (member (strcase DosLibVer T) (arx)))
			(if (findfile DosLibVer)
				(arxload DosLibVer)
				(princ "\n*Buttons Error*: DosLIB Arx file not found on this system!")
			)
		)
	)
;;;	Initialize common variables for all applications.
	(setq	dlg		2
			Cnt		65
			HdVal	nil
			NdVal	nil
			NamVal	nil
			DrLst	(dos_drives)
			ActLst	(list nil nil nil)
	)
;;;	Check to see which Application is running and makes application specific selection, setting, actions, etc.	
	(cond
		((or (wcmatch (StpDot AppNam) "CADET##")(=(StpDot AppNam) "CADET"))
;;; CET 07/26/2007 Removed If statements replaced with select before repeat same calls.			
			(if Cadet_Net
				(setq	NdVal	(substr Cadet_Net 1 2)
						NdVal	(- (length DrLst) (length (member NdVal DrLst)))
						NdVal	(itoa NdVal)
				)
			)
			(if Cadet_HD
				(setq	HdVal	(substr Cadet_HD 1 2)
						HdVal	(- (length DrLst) (length (member HdVal DrLst)))
						HdVal	(itoa HdVal)
				)
			)
			(if (setq Dcl_Pan (findfile "Get_Init.dcl"))
				(if (> (setq Dcl_Pan (load_dialog Dcl_Pan)) 0)
					(while (> dlg 1)
						(new_dialog "INIEditCadet" Dcl_Pan)
						(start_list "Lst1" 3)
						(mapcar (quote add_list) DrLst)
						(end_list)
						(start_list "Lst2" 3)
						(mapcar (quote add_list) DrLst)
						(end_list)
						(if HdVal
							(set_tile "Lst1" HdVal)
						)
						(if NdVal
							(set_tile "Lst2" NdVal)
						)
						(if Cadet_User
							(set_tile "Str3" Cadet_User)
							(if (getenv "USERNAME")
								(set_tile "Str3" (getenv "USERNAME"))
								(set_tile "Str3" (strcase (getvar "loginname")))
							)
						)
						(if (and HdVal NdVal Cadet_User)
							(setq	ActLst	(list	(get_tile "Lst1")
													(get_tile "Lst2")
													(get_tile "Str3")
											)
							)
						)
						(Cb_Ok nil nil ActLst)
						(action_tile "Lst1" "(setq ActLst (Cb_Ok 1 $value ActLst))")
						(action_tile "Lst2" "(setq ActLst (Cb_Ok 2 $value ActLst))")
						(action_tile "Str3" "(setq ActLst (Cb_Ok 3 $value ActLst))")
						(action_tile "ok_button" "(done_dialog 1)")
						(setq dlg (start_dialog))
						(unload_dialog Dcl_Pan)
					)
					(alert "\nUnable to open DCL file")
				)
				(alert "\nUnable to find DCL file")
			)
			(if (and (nth 0 ActLst) (nth 1 ActLst) (nth 2 ActLst))
				(progn
					(if (or (not Cadet_HD) (= Cadet_HD "default"))
						(if	(member "CADET20" (mapcar (quote strcase) (dos_subdir (strcat (nth (atoi (nth 0 ActLst)) DrLst) "\\"))))
							(setq	Cadet_HD		(strcat (nth (atoi (nth 0 ActLst)) DrLst) "\\CADET20\\"))
							(setq	Cadet_HD		(strcat (nth (atoi (nth 0 ActLst)) DrLst) "\\"))
						)
					)
					(if (or (not Cadet_Old) (= Cadet_Old "default"))
						(if (member "CADET" (mapcar (quote strcase) (dos_subdir (strcat (nth (atoi (nth 1 ActLst)) DrLst) "\\"))))
							(setq	Cadet_Old	(strcat (nth (atoi (nth 1 ActLst)) DrLst) "\\CADET\\"))
							(setq	Cadet_Old	(strcat (nth (atoi (nth 1 ActLst)) DrLst) "\\"))
						)
					)
					(if (or (not Cadet_Net) (= Cadet_Net "default"))
						(progn
							(if (member "DIVMAP10" (mapcar (quote strcase) (dos_subdir (strcat (nth (atoi (nth 1 ActLst)) DrLst) "\\"))))
								(setq	Cadet_Net	(strcat (nth (atoi (nth 1 ActLst)) DrLst) "\\DIVMAP10\\"))
								(setq	Cadet_Net	(strcat (nth (atoi (nth 1 ActLst)) DrLst) "\\"))
							)
							(if (member "CADET20" (mapcar (quote strcase) (dos_subdir Cadet_Net)))
								(setq	Cadet_Net		(strcat Cadet_Net "CADET20\\"))
								(setq	Cadet_Net		(strcat Cadet_Net))
							)
						)
					)
					(setq	Cadet_User	(nth 2 ActLst))
					(if (not _Path-Dwg)
						(if (member "DWG" (mapcar (quote strcase) (dos_subdir Cadet_Old)))
							(setq	_Path-Dwg		(strcat Cadet_Old "DWG\\"))
							(setq	_Path-Dwg		(strcat Cadet_Old))
						)
					)
					(if (not _Path-Plot)
						(if (member "PLOT" (mapcar (quote strcase) (dos_subdir Cadet_Old)))
							(setq	_Path-Plot	(strcat Cadet_Old "PLOT\\"))
							(setq	_Path-Plot	(strcat Cadet_Old))
						)
					)
					(if (not _Path-User)
						(if (member "USER" (mapcar (quote strcase) (dos_subdir Cadet_Old)))
							(setq	_Path-User	(strcat Cadet_Old "USER\\"))
							(setq	_Path-User	(strcat Cadet_Old))
						)
					)
					(if (not _Path-Lisp)
						(if (member "LISP" (mapcar (quote strcase) (dos_subdir Cadet_Net)))
							(setq	_Path-Lisp	(strcat Cadet_Net "LISP\\"))
							(setq	_Path-Lisp	(strcat Cadet_Net))
						)
					)
					(if (not _Path-LUT)
						(if (member "LUT" (mapcar (quote strcase) (dos_subdir Cadet_Net)))
							(setq	_Path-LUT		(strcat Cadet_Net "LUT\\"))
							(setq	_Path-LUT		(strcat Cadet_Net))
						)
					)
					(if (not _Path-Menu)
						(if (member "MENU" (mapcar (quote strcase) (dos_subdir Cadet_Net)))
							(setq	_Path-Menu	(strcat Cadet_Net "MENU\\"))
							(setq	_Path-Menu	(strcat Cadet_Net))
						)
					)
					(if (not _Path-Sym)
						(if (member "SYM" (mapcar (quote strcase) (dos_subdir Cadet_Net)))
							(setq	_Path-Sym		(strcat Cadet_Net "SYM\\"))
							(setq	_Path-Sym		(strcat Cadet_Net))
						)
					)
					;	Populates list for intial values in path dialog box later in this function.
					(setq	PthLst	(list	_Path-Person	;  0 INI Section -
											Cadet_HD		;  1 INI Section -
											_Path-Dwg		;  2 INI Section -
											_Path-Plot	;  3 INI Section -
											_Path-User	;  4 INI Section -
											_Path-Lisp	;  5 INI Section -
											_Path-LUT		;  6 INI Section -
											_Path-Menu	;  7 INI Section -
											_Path-Sym		;  8 INI Section -
									)
					)
					(setq	GoPath	T
							dlg		2
					)
				)
			)
		)
		((= (StpDot AppNam) "ADDS")
				(progn
					(princ "\n - PathDlg - start")
					
					(cond 
						((= Div "AL")
							setq	Adds_Net		(strcat "S:\\WorkGroups\\" (DecodeDivisionPath) "\\Transmap\\ADDS_TMap\\"(StpDot AppNam) "\\")
						)
						((= Div "GA")
							setq	Adds_Net		(strcat "S:\\WorkGroups\\" (DecodeDivisionPath) "\\STAFF\\Transmap\\ADDS_TMap\\"(StpDot AppNam) "\\")
						)
						(t
							setq	Adds_Net		(strcat "S:\\WorkGroups\\" (DecodeDivisionPath) "\\Division Mapping\\"(StpDot AppNam) "\\")
						)
					)	
							
				    (setq		Adds_Local	"C:\\Div_Map\\"
							Adds_HD		(strcat "C:\\" (StpDot AppNam) "\\")
					)
					
					;	This section builds default path if _Path-xxx does not exists.
					(if (not _Path-Person)
						(setq	_Path-Person	Adds_Local)
					)
					(if (not AppDwtNam)
						(if (member "LookUpTable" (mapcar (quote strcase) (dos_subdir Adds_Local)))
							(if (member "Templete" (mapcar (quote strcase) (dos_subdir (strcat Adds_Local "LookUpTable"))))
								(setq	AppDwtNam (strcat Adds_Local "LookUpTable\\"))
							)
						)
					)
					(if (not _Path-Dwg)
						(if (member "DWG" (mapcar (quote strcase) (dos_subdir Adds_Net)))
							(setq	_Path-Dwg		(strcat Adds_Net "DWG\\"))
							(setq	_Path-Dwg		(strcat Adds_Net))
						)
					)
					(if (not _Path-DWF)
						(if (member "DWF" (mapcar (quote strcase) (dos_subdir Adds_Net)))
							(setq	_Path-DWF	(strcat Adds_Net "DWF\\"))
							(setq	_Path-DWF	(strcat Adds_Net))
						)
					)
					(if (not _Path-User)
						(if (member "USER" (mapcar (quote strcase) (dos_subdir (strcat Adds_Local (StpDot AppNam)))))
							(setq	_Path-User	(strcat Adds_Local (StpDot AppNam) "\\USER\\"))
							(setq	_Path-User	(strcat Adds_Old))
						)
					)
					(if (not _Path-Plot)
						(if (member "PLOT" (mapcar (quote strcase) (dos_subdir Adds_Net)))
							(setq	_Path-Plot	(strcat Adds_Net "PLOT\\"))
							(setq	_Path-Plot	(strcat Adds_Net))
						)
					)
					(if (not _Path-Lisp)
						(if (member "LISP" (mapcar (quote strcase) (dos_subdir (strcat Adds_Local (StpDot AppNam)))))
							(setq	_Path-Lisp	(strcat Adds_Local (StpDot AppNam) "\\LISP\\"))
							(setq	_Path-Lisp	(strcat Adds_Local (StpDot AppNam) "\\"))
						)
					)
					(if (not _Path-LUT)
						(if (member "LUT" (mapcar (quote strcase) (dos_subdir (strcat Adds_Local (StpDot AppNam)))))
							(setq	_Path-LUT		(strcat Adds_Local (StpDot AppNam) "\\LUT\\"))
							(setq	_Path-LUT		(strcat Adds_Local (StpDot AppNam) "\\"))
						)
					)
					(if (not _Path-Menu)
						(if (member "MENU" (mapcar (quote strcase) (dos_subdir (strcat Adds_Local (StpDot AppNam)))))
							(setq	_Path-Menu	(strcat Adds_Local (StpDot AppNam) "\\MENU\\"))
							(setq	_Path-Menu	(strcat Adds_Local (StpDot AppNam) "\\"))
						)
					)
					(if (not _Path-Sym)
						(if (member "SYM" (mapcar (quote strcase) (dos_subdir (strcat Adds_Local (StpDot AppNam)))))
							(setq	_Path-Sym		(strcat Adds_Local (StpDot AppNam) "\\SYM\\"))
							(setq	_Path-Sym		(strcat Adds_Local (StpDot AppNam) "\\"))
						)
					)
					(if (not _Path-DLG)
						(if (member "DLG" (mapcar (quote strcase) (dos_subdir (strcat Adds_Local (StpDot AppNam)))))
							(setq	_Path-DLG		(strcat Adds_Local (StpDot AppNam) "\\DLG\\"))
							(setq	_Path-DLG		(strcat Adds_Local (StpDot AppNam) "\\"))
						)
					)
					
					(setq	PthLst	(list	_Path-Person		;  0 INI Section - Person
											Adds_HD			;  1 INI Section - Not currently used in Adds
											_Path-Dwg			;  2 INI Section - Dwg
											_Path-Plot		;  3 INI Section - Plot
											_Path-User		;  4 INI Section - UserP
											_Path-Lisp		;  5 INI Section - Lisp
											_Path-LUT			;  6 INI Section - LUT
											_Path-Menu		;  7 INI Section - Menu
											_Path-Sym			;  8 INI Section - Sym
											_Path-DLG			;  9 INI Section - Dlg
											_Path-DWF			; 10 INI Section - Dwf
											AppDwtNam			; 11 INI Section - DwtNam
									)
					)
					(setq	GoPath	T
							dlg		2
					)
					(princ "\n - PathDlg - end")
				)
		)
		((= (strcase (substr AppNam 1 5)) "ADDSP")
;;; CET 07/26/2007 Removed If statements replaced with select before repeat same calls.			
			(if Adds_Net
				(setq	NdVal	(substr Adds_Net 1 2)
						NdVal	(- (length DrLst) (length (member NdVal DrLst)))
						NdVal	(itoa NdVal)
				)
			)
			(if Adds_HD
				(setq	HdVal	(substr Adds_HD 1 2)
						HdVal	(- (length DrLst) (length (member HdVal DrLst)))
						HdVal	(itoa HdVal)
				)
			)
			(if (setq Dcl_Pan (findfile "Get_Init.dcl"))
				(if (> (setq Dcl_Pan (load_dialog Dcl_Pan)) 0)
					(while (> dlg 1)
						(new_dialog "INIEditAdds" Dcl_Pan)
						(start_list "Lst1" 3)
						(mapcar (quote add_list) DrLst)
						(end_list)
						(start_list "Lst2" 3)
						(mapcar (quote add_list) DrLst)
						(end_list)
						(if HdVal
							(set_tile "Lst1" HdVal)
						)
						(if NdVal
							(set_tile "Lst2" NdVal)
						)
						(if Adds_User
							(set_tile "Str3" Adds_User)
							(if (getenv "USERNAME")
								(set_tile "Str3" (getenv "USERNAME"))
								(set_tile "Str3" (strcase (getvar "loginname")))
							)
						)
						(if (and HdVal NdVal Adds_User)
							(setq	ActLst	(list	(get_tile "Lst1")
													(get_tile "Lst2")
													(get_tile "Str3")
											)
							)
						)
						(Cb_Ok nil nil ActLst)
						(action_tile "Lst1" "(setq ActLst (Cb_Ok 1 $value ActLst))")
						(action_tile "Lst2" "(setq ActLst (Cb_Ok 2 $value ActLst))")
						(action_tile "Str3" "(setq ActLst (Cb_Ok 3 $value ActLst))")
						(action_tile "ok_button" "(done_dialog 1)")
						(setq dlg (start_dialog))
						(unload_dialog Dcl_Pan)
					)
					(alert "\nUnable to open DCL file")
				)
				(alert "\nUnable to find DCL file")
			)
			(if (and (nth 0 ActLst) (nth 1 ActLst) (nth 2 ActLst) (= dlg 1))
				(progn
					(if (not Adds_HD)
						(if	(member "ADDSPLOT" (mapcar 'strcase (dos_subdir (strcat (nth (atoi (nth 0 ActLst)) DrLst) "\\"))))
							(setq	Adds_HD		(strcat (nth (atoi (nth 0 ActLst)) DrLst) "\\ADDSPLOT\\"))
							(setq	Adds_HD		(strcat (nth (atoi (nth 0 ActLst)) DrLst) "\\"))
						)
					)
					(if (not Adds_Old)
						(if (member "ADDS" (mapcar (quote strcase) (dos_subdir (strcat (nth (atoi (nth 1 ActLst)) DrLst) "\\"))))
							(setq	Adds_Old	(strcat (nth (atoi (nth 1 ActLst)) DrLst) "\\ADDS\\"))
							(setq	Adds_Old	(strcat (nth (atoi (nth 1 ActLst)) DrLst) "\\"))
						)
					)
					(if (not Adds_Net)
						(progn
							(if (member "DIV_MAP" (mapcar (quote strcase) (dos_subdir (strcat (nth (atoi (nth 1 ActLst)) DrLst) "\\"))))
								(setq	Adds_Net	(strcat (nth (atoi (nth 1 ActLst)) DrLst) "\\DIV_MAP\\"))
								(setq	Adds_Net	(strcat (nth (atoi (nth 1 ActLst)) DrLst) "\\"))
							)
							(if (< (strlen Adds_Net) 5) (princ (strcat "\nAdds_Net:" Adds_Net)))
							(if (member "ADDSPLOT" (mapcar 'strcase (dos_subdir Adds_Net)))
								(setq	Adds_Net		(strcat Adds_Net "ADDSPLOT\\"))
								(setq	Adds_Net		(strcat Adds_Net))
							)
						)
					)
					(setq	Adds_User	(nth 2 ActLst))
					(if (not _Path-Dwg)
						(if (member "DWG" (mapcar (quote strcase) (dos_subdir Adds_Net)))
							(setq	_Path-Dwg		(strcat Adds_Net "DWG\\"))
							(setq	_Path-Dwg		(strcat Adds_Net))
						)
					)
					(if (not _Path-Plot)
						(if (member "PLOT" (mapcar (quote strcase) (dos_subdir Adds_Old)))
							(setq	_Path-Plot	(strcat Adds_Old "PLOT\\"))
							(setq	_Path-Plot	(strcat Adds_Old))
						)
					)
					(if (not _Path-User)
						(if (member "USER" (mapcar (quote strcase) (dos_subdir Adds_Old)))
							(setq	_Path-User	(strcat Adds_Old "USER\\"))
							(setq	_Path-User	(strcat Adds_Old))
						)
					)
					(if (not _Path-Lisp)
						(if (member "LISP" (mapcar (quote strcase) (dos_subdir Adds_Net)))
							(setq	_Path-Lisp	(strcat Adds_Net "LISP\\"))
							(setq	_Path-Lisp	(strcat Adds_Net))
						)
					)
					(if (not _Path-LUT)
						(if (member "LUT" (mapcar (quote strcase) (dos_subdir Adds_Net)))
							(setq	_Path-LUT		(strcat Adds_Net "LUT\\"))
							(setq	_Path-LUT		(strcat Adds_Net))
						)
					)
					(if (not _Path-Menu)
						(if (member "MENU" (mapcar (quote strcase) (dos_subdir Adds_Net)))
							(setq	_Path-Menu	(strcat Adds_Net "MENU\\"))
							(setq	_Path-Menu	(strcat Adds_Net))
						)
					)
					(if (not _Path-Sym)
						(if (member "SYM" (mapcar (quote strcase) (dos_subdir Adds_Net)))
							(setq	_Path-Sym		(strcat Adds_Net "SYM\\"))
							(setq	_Path-Sym		(strcat Adds_Net))
						)
					)
					(if (not _Path-DLG)
						(if (member "DLG" (mapcar (quote strcase) (dos_subdir Adds_Net)))
							(setq	_Path-DLG		(strcat Adds_Net "DLG\\"))
							(setq	_Path-DLG		(strcat Adds_Net))
						)
					)
					(if (not _Path-DWF)
						(if (member "DWF" (mapcar (quote strcase) (dos_subdir Adds_Net)))
							(setq	_Path-DWF	(strcat Adds_Net "DWF\\"))
							(setq	_Path-DWF	(strcat Adds_Net))
						)
					)
					(if (not AppDwtNam)
						(if (member "DWT" (mapcar (quote strcase) (dos_subdir Adds_Net)))
							(setq	AppDwtNam (strcat Adds_Net  "LUT\\Template\\"))
							(setq	_Path-DWF	(strcat Adds_Net))

						)
					)
					(setq	PthLst	(list	_Path-Person	;  0 INI Section - Person
											Adds_HD		;  1 INI Section -
											_Path-Dwg		;  2 INI Section -
											_Path-Plot	;  3 INI Section -
											_Path-User	;  4 INI Section -
											_Path-Lisp	;  5 INI Section -
											_Path-LUT		;  6 INI Section -
											_Path-Menu	;  7 INI Section -
											_Path-Sym		;  8 INI Section -
											_Path-DLG		;  9 INI Section -
											_Path-DWF		; 10 INI Section -
											AppDwtNam		; 11 INI Section -
									)
					)
					(setq	GoPath	T
							dlg		2
					)
				)
				(setq	GoPath	nil
						Bubba	(princ "\nUpDate Path cancelled")
				)
			)
		)
	)	;;; End of Select for checking to see which Application is running
;;;	CET 07/27/2007 Move common results actions out of Application code cheching block. 
;(getstring "What's up Doc?")
;;;	Display Dialog box for user to review/change default paths.
	(if GoPath
		(if (setq Dcl_Pan (findfile "Get_Init.dcl"))
			(if (> (setq Dcl_Pan (load_dialog Dcl_Pan)) 0)
				(while (> dlg 1)
					(cond 
						((or (wcmatch (StpDot AppNam) "CADET##") (= (StpDot AppNam) "CADET"))
							(new_dialog "INIPathCadet" Dcl_Pan)
						)
						((=(StpDot AppNam) "ADDSPLOT")
							(new_dialog "INIPathAddsPlot" Dcl_Pan)
						)
						(T
							(new_dialog "INIPathAdds" Dcl_Pan)
						)
					)
					(Cb_Lst nil nil nil)
					(action_tile "Pth1" "(setq PthLst (Cb_Lst 0 $value PthLst))")
					(action_tile "Pth2" "(setq PthLst (Cb_Lst 1 $value PthLst))")
					(action_tile "Pth3" "(setq PthLst (Cb_Lst 2 $value PthLst))")
					(action_tile "Pth4" "(setq PthLst (Cb_Lst 3 $value PthLst))")
					(action_tile "Pth5" "(setq PthLst (Cb_Lst 4 $value PthLst))")
					(action_tile "Pth6" "(setq PthLst (Cb_Lst 5 $value PthLst))")
					(action_tile "Pth7" "(setq PthLst (Cb_Lst 6 $value PthLst))")
					(action_tile "Pth8" "(setq PthLst (Cb_Lst 7 $value PthLst))")
					(action_tile "Pth9" "(setq PthLst (Cb_Lst 8 $value PthLst))")
					(if (/=(or (wcmatch (StpDot AppNam) "CADET##") (wcmatch (StpDot AppNam) "CADET")))
						(progn 
							(action_tile "Pth10" "(setq PthLst (Cb_Lst 9 $value PthLst))")
							(action_tile "Pth11" "(setq PthLst (Cb_Lst 10 $value PthLst))")
							(action_tile "Pth12" "(setq PthLst (Cb_Lst 11 $value PthLst))")
							(action_tile "Pth13" "(setq PthLst (Cb_Lst 12 $value PthLst))")
							(action_tile "Pth14" "(setq PthLst (Cb_Lst 13 $value PthLst))")
						)
					)
					(action_tile "ok_button" "(done_dialog 1)")
					(setq dlg (start_dialog))
					(unload_dialog Dcl_Pan)
				)
				(alert "\nUnable to open DCL file")
			)
			(alert "\nUnable to find DCL file")
		)
		(alert "\nUnable to find GoPath! Last")
	)

;;;	Set paths based on dialog result OK Button being clicked. 
	(if (= Dlg 1)
		(progn
			(if (nth 0 PthLst)
				(setq	_Path-Person	(nth 0 PthLst))
			)
			(if (nth 1 PthLst)
				(progn
					(if (wcmatch (StpDot AppNam) "CADET*")
						(setq	Cadet_HD		(nth 1 PthLst))
					)
					(if (wcmatch (StpDot AppNam) "ADDSPLOT*")
						(setq	Adds_HD		(nth 1 PthLst))
					)
				)
			)
			(if (nth 2 PthLst)
				(setq	_Path-Dwg 	(nth 2 PthLst))
			)
			(if (nth 3 PthLst)
				(setq	_Path-Plot	(nth 3 PthLst))
			)
			(if (nth 4 PthLst)
				(setq	_Path-User	(nth 4 PthLst))
			)
			(if (nth 5 PthLst)
				(setq	_Path-Lisp	(nth 5 PthLst))
			)
			(if (nth 6 PthLst)
				(setq	_Path-LUT		(nth 6 PthLst))
			)
			(if (nth 7 PthLst)
				(setq	_Path-Menu	(nth 7 PthLst))
			)
			(if (nth 8 PthLst)
				(setq	_Path-Sym		(nth 8 PthLst))
			)
			(if (/=(or (wcmatch (StpDot AppNam) "CADET##") (wcmatch (StpDot AppNam) "CADET")))
				(progn 
					(if (nth 9 PthLst)
						(setq	_Path-DLG		(nth 9 PthLst))
					)
					(if (nth 10 PthLst)
						(setq	_Path-DWF		(nth 10 PthLst))
					)
					(if (nth 11 PthLst)
						(setq	AppDwtNam		(nth 11 PthLst))
					)
				)
			)
			(if Bug (princ "\nPaths Set!"))
		)
	)
	(if (and Bug PthLst)
		(setq	EdsLst	PthLst)
	)
	(if (= Dlg 1)
		PthLst
		nil
	)
)

(defun TstPth ( DrvInf /	GoodDrv Drv Sub	; Path Test function to validate Paths in Call Back
						Fil Ext SubLen SubTst
						SubLst Cnt Strt Bubba )
	(setq	GoodDrv	T
			Drv		(nth 0 DrvInf)
			Sub		(nth 1 DrvInf)
			Fil		(nth 2 DrvInf)
			Ext		(nth 3 DrvInf)
			Drv		(strcat Drv (substr Sub 1 1))
	)
	(if (and Bug Drv) (princ (strcat "\nDrive: " Drv)))
	(if (and Bug Sub) (princ (strcat "\nSub: " Sub)))
	(if (< (strlen Sub) 2)
		(setq	Sub		nil)
		(setq	Sub		(substr Sub 2)
				SubLen	(strlen Sub)
				SubTst	Drv
				SubLst	(mapcar (quote strcase) (dos_subdir SubTst))
				Cnt		1
				Strt		1
		)
	)
	(if (not (member (substr Drv 1 2) (mapcar (quote strcase) (dos_drives))))
		(setq	GoodDrv	nil
				Bubba	(if Bug (princ "\nDrive is Bad!"))
		)
		(if Bug (princ "\nDrive is Good!"))
	)
	(if Bug (princ "\nTesting Path..."))
	(if Sub
		(while (<= Cnt SubLen)
			(if	(and	(/= Cnt 1)
					(= (substr Sub Cnt 1) "\\")
				)
				(setq	Psub		(substr Sub Strt (- Cnt Strt))
						Strt		(1+ Cnt)
				)
				(setq	Psub		nil)
			)
			(if (and Bug Psub) (princ (strcat "\nPsub:" Psub " Strt:" (itoa Strt) " Cnt:" (itoa Cnt)"!")))
			(if Psub
				(if GoodDrv
					(if (not (member (strcase Psub) SubLst))
						(setq	GoodDrv		nil)
						(setq	Bubba	(if Bug (princ (strcat "\nTested " Psub " Good!")))
								SubTst	(strcat SubTst Psub "\\")
								Bubba	(if Bug (princ (strcat "\nSubTst:" SubTst)))
								SubLst	(mapcar (quote strcase) (dos_subdir SubTst))
								Psub		nil
						)
					)
				)
			)
			(setq	Cnt	(1+ Cnt))
		)
	)
	GoodDrv
)

(defun Cb_Lst ( Act ValP DoLst / IsGood Pth )	; Call Back - INI path tester
	(cond
		((or(= (StpDot AppNam) "CADET20") (=(StpDot AppNam) "CADET"))
			(if (and (>= Act 0) (<= Act 8))
				(progn
					(setq	IsGood	T)
					(if (not (TstPth (dos_splitpath ValP)))
						(setq	IsGood	nil)
					)
					(if IsGood
						(mode_tile "ok_button" 0)
						(mode_tile "ok_button" 1)
					)
					(if Bug
						(if IsGood
							(princ "\nIts Good!")
							(princ "\nIts No Good!")
						)
					)
					(if IsGood
						(setq	DoLst	(RepLst DoLst ValP Act))
						(set_tile (strcat "Pth" (itoa (1+ Act))) (nth Act DoLst))
					)
				)
				(setq	DoLst	DoLst)
			)
			(if (null Act)
				(progn
					(set_tile "Pth1" (nth 0 PthLst))
					(set_tile "Pth2" (nth 1 PthLst))
					(set_tile "Pth3" (nth 2 PthLst))
					(set_tile "Pth4" (nth 3 PthLst))
					(set_tile "Pth5" (nth 4 PthLst))
					(set_tile "Pth6" (nth 5 PthLst))
					(set_tile "Pth7" (nth 6 PthLst))
					(set_tile "Pth8" (nth 7 PthLst))
					(set_tile "Pth9" (nth 8 PthLst))
					(setq	IsGood	T)
					(foreach	Pth
							DoLst
							(if IsGood
								(if (not (TstPth (dos_splitpath Pth)))
									(setq	IsGood	nil)
								)
							)
					)
					(if IsGood
						(mode_tile "ok_button" 0)
						(mode_tile "ok_button" 1)
					)
					(if Bug
						(if IsGood
							(princ "\nIts Good!")
							(princ "\nIts No Good!")
						)
					)
				)
			)
		)
		((= (strcase (substr AppNam 1 5)) "ADDS ")
			(if (and (>= Act 0) (<= Act 13))
				(progn
					(setq	IsGood	T)
					(if (not (TstPth (dos_splitpath ValP)))
						(setq	IsGood	nil)
					)
					(if IsGood
						(mode_tile "ok_button" 0)
						(mode_tile "ok_button" 1)
					)
					(if Bug
						(if IsGood
							(princ "\nIts Good!")
							(princ "\nIts No Good!")
						)
					)
					(if IsGood
						(setq	DoLst	(RepLst DoLst (strcase ValP) Act)
								Bubba	(set_tile (strcat "Pth" (itoa (1+ Act))) (nth Act DoLst))
						)
						(set_tile (strcat "Pth" (itoa (1+ Act))) (nth Act DoLst))
					)
				)
				(setq	DoLst	DoLst)
			)
			(if (null Act)
				(progn
					(set_tile "Pth1" (nth 0 PthLst))
					(set_tile "Pth2" (nth 1 PthLst))
					(set_tile "Pth3" (nth 2 PthLst))
					(set_tile "Pth4" (nth 3 PthLst))
					(set_tile "Pth5" (nth 4 PthLst))
					(set_tile "Pth6" (nth 5 PthLst))
					(set_tile "Pth7" (nth 6 PthLst))
					(set_tile "Pth8" (nth 7 PthLst))
					(set_tile "Pth9" (nth 8 PthLst))
					(set_tile "Pth10" (nth 9 PthLst))
					(set_tile "Pth11" (nth 10 PthLst))
					(set_tile "Pth12" (nth 11 PthLst))
;					(set_tile "Pth13" (nth 12 PthLst))
;					(set_tile "Pth14" (nth 13 PthLst))
					(setq	IsGood	T)
					(foreach	Pth
							DoLst
							(if IsGood
								(if (not (TstPth (dos_splitpath Pth)))
									(setq	IsGood	nil)
								)
							)
					)
					(if IsGood
						(mode_tile "ok_button" 0)
						(mode_tile "ok_button" 1)
					)
					(if Bug
						(if IsGood
							(princ "\nIts Good!")
							(princ "\nIts No Good!")
						)
					)
				)
			)
		)
		((= (strcase (substr AppNam 1 5)) "ADDSP")
			(if (and (>= Act 0) (<= Act 13))
				(progn
					(setq	IsGood	T)
					(if (not (TstPth (dos_splitpath ValP)))
						(setq	IsGood	nil)
					)
					(if IsGood
						(mode_tile "ok_button" 0)
						(mode_tile "ok_button" 1)
					)
					(if Bug
						(if IsGood
							(princ "\nIts Good!")
							(princ "\nIts No Good!")
						)
					)
					(if IsGood
						(setq	DoLst	(RepLst DoLst (strcase ValP) Act)
								Bubba	(set_tile (strcat "Pth" (itoa (1+ Act))) (nth Act DoLst))
						)
						(set_tile (strcat "Pth" (itoa (1+ Act))) (nth Act DoLst))
					)
				)
				(setq	DoLst	DoLst)
			)
			(if (null Act)
				(progn
					(set_tile "Pth1" (nth 0 PthLst))
					(set_tile "Pth2" (nth 1 PthLst))
					(set_tile "Pth3" (nth 2 PthLst))
					(set_tile "Pth4" (nth 3 PthLst))
					(set_tile "Pth5" (nth 4 PthLst))
					(set_tile "Pth6" (nth 5 PthLst))
					(set_tile "Pth7" (nth 6 PthLst))
					(set_tile "Pth8" (nth 7 PthLst))
					(set_tile "Pth9" (nth 8 PthLst))
					(set_tile "Pth10" (nth 9 PthLst))
					(set_tile "Pth11" (nth 10 PthLst))
					(set_tile "Pth12" (nth 11 PthLst))
;					(set_tile "Pth13" (nth 12 PthLst))
;					(set_tile "Pth14" (nth 13 PthLst))
					(setq	IsGood	T)
					(foreach	Pth
							DoLst
							(if IsGood
								(if (not (TstPth (dos_splitpath Pth)))
									(setq	IsGood	nil)
								)
							)
					)
					(if IsGood
						(mode_tile "ok_button" 0)
						(mode_tile "ok_button" 1)
					)
					(if Bug
						(if IsGood
							(princ "\nIts Good!")
							(princ "\nIts No Good!")
						)
					)
				)
			)
		)
	)
	DoLst
)

(defun Cb_Ok ( Act ValP DoLst / )				; Call Back function for PathDLG
	(cond
		((= Act 1) (setq	DoLst	(list ValP (nth 1 DoLst) (nth 2 DoLst))))
		((= Act 2) (setq	DoLst	(list (nth 0 DoLst) ValP (nth 2 DoLst))))
		((= Act 3) (setq	DoLst	(list (nth 0 DoLst) (nth 1 DoLst) ValP)))
		((null Act)(setq	DoLst	(list (get_tile "Lst1") (get_tile "Lst2") (get_tile "Str3"))))
	)
	(if (or		(= "" (get_tile "Lst1"))
				(= "0" (get_tile "Lst1"))
				(= " " (get_tile "Lst1"))
				(= "" (get_tile "Lst2"))
				(= "0" (get_tile "Lst2"))
				(= " " (get_tile "Lst2"))
				(< (strlen (get_tile "Str3")) 1)
		)
		(mode_tile "ok_button" 1)
		(mode_tile "ok_button" 0)
	)
	(if Bug
		(progn
			(if (or (= "" (get_tile "Lst1")) (= "0" (get_tile "Lst1")) (= " " (get_tile "Lst1")))
				(princ "\nBlank HdVal!")
				(princ (strcat "\n" (get_tile "Lst1") " HdVal!"))
			)
			(if (or (= "" (get_tile "Lst2")) (= "0" (get_tile "Lst2")) (= " " (get_tile "Lst2")))
				(princ "\nBlank NdVal!")
				(princ (strcat "\n" (get_tile "Lst2") " NdVal!"))
			)
			(if (< (strlen (get_tile "Str3")) 1)
				(princ "\nNot Over 0 NamVal!")
				(princ (strcat "\n" (get_tile "Str3") " NamVal!"))
			)
		)
	)
	DoLst
)

(defun DivSet ( Ch /	Bubba Cnt InData Hdr x	; Allows Selection of Division from parameter
					Fn F0 F1 Dsc Div_Lst
					DivINI DivNam TmpVal TmpDiv )
	(if Bug (princ "Entering DivSet!"))
	(setq	DivINI	(strcat _Path-Person "DIV_MAP.INI")
			Div_Lst	(list	"BH" "S_" "W_" "E_" "M_" "SE" "AL" "GA")
			TDiv		nil
			Div_Pth	(list	nil nil nil nil nil nil)
	)
	(if (findfile DivINI)
		(progn
			(if (setq TmpDiv (dos_getini (StpDot AppNam) (strcat "BH" ".DIVISION") DivINI))
				(if (= (substr TmpDiv 1 1) "*")
					(setq	Div_Pth	(RepLst Div_Pth (cons "BH" (substr TmpDiv 2)) 0)
							TDiv		0
					)
					(setq	Div_Pth	(RepLst Div_Pth (cons "BH" TmpDiv) 0))
				)
				(setq	Div_Pth	(RepLst Div_Pth (cons "BH" "") 0))
			)
			(if (setq TmpDiv (dos_getini (StpDot AppNam) (strcat "S_" ".DIVISION") DivINI))
				(if (= (substr TmpDiv 1 1) "*")
					(setq	Div_Pth	(RepLst Div_Pth (cons "S_" (substr TmpDiv 2)) 1)
							TDiv		1
					)
					(setq	Div_Pth	(RepLst Div_Pth (cons "S_" TmpDiv) 1))
				)
				(setq	Div_Pth	(RepLst Div_Pth (cons "S_" "") 1))
			)
			(if (setq TmpDiv (dos_getini (StpDot AppNam) (strcat "W_" ".DIVISION") DivINI))
				(if (= (substr TmpDiv 1 1) "*")
					(setq	Div_Pth	(RepLst Div_Pth (cons "W_" (substr TmpDiv 2)) 2)
							TDiv		2
					)
					(setq	Div_Pth	(RepLst Div_Pth (cons "W_" TmpDiv) 2))
				)
				(setq	Div_Pth	(RepLst Div_Pth (cons "W_" "") 2))
			)
			(if (setq TmpDiv (dos_getini (StpDot AppNam) (strcat "E_" ".DIVISION") DivINI))
				(if (= (substr TmpDiv 1 1) "*")
					(setq	Div_Pth	(RepLst Div_Pth (cons "E_" (substr TmpDiv 2)) 3)
							TDiv		3
					)
					(setq	Div_Pth	(RepLst Div_Pth (cons "E_" TmpDiv) 3))
				)
				(setq	Div_Pth	(RepLst Div_Pth (cons "E_" "") 3))
			)
			(if (setq TmpDiv (dos_getini (StpDot AppNam) (strcat "M_" ".DIVISION") DivINI))
				(if (= (substr TmpDiv 1 1) "*")
					(setq	Div_Pth	(RepLst Div_Pth (cons "M_" (substr TmpDiv 2)) 4)
							TDiv		4
					)
					(setq	Div_Pth	(RepLst Div_Pth (cons "M_" TmpDiv) 4))
				)
				(setq	Div_Pth	(RepLst Div_Pth (cons "M_" "") 4))
			)
			(if (setq TmpDiv (dos_getini (StpDot AppNam) (strcat "SE" ".DIVISION") DivINI))
				(if (= (substr TmpDiv 1 1) "*")
					(setq	Div_Pth	(RepLst Div_Pth (cons "SE" (substr TmpDiv 2)) 5)
							TDiv		5
					)
					(setq	Div_Pth	(RepLst Div_Pth (cons "SE" TmpDiv) 5))
				)
				(setq	Div_Pth	(RepLst Div_Pth (cons "SE" "") 5))
			)
			(setq	Dlg	2)
		)
	)
	(if (assoc Ch Div_Lst)
		(setq	Div			Ch
				DivINI		(strcat _Path-Person "DIV_MAP.INI")
				_Path-Div		(cdr (assoc Ch Div_Lst))
				_Path-Panel	_Path-Div
		)
		(progn
			(alert (strcat "***" AppNam " Error***\nNot a valid Division Choice!"))
			(exit)
		)
	)
	(if (assoc Ch Div_Lst)
		(setvar "USERS3" Div)
	)
	(cond	((= Div "AL") (princ "\nAlabama Control Center Selected"))
			((= Div "GA") (princ "\nGeorgia Control Center Selected"))
			((= Div "BH") (princ "\nBirmingham Division Selected"))
			((= Div "S_") (princ "\nSouthern Division Selected"))
			((= Div "W_") (princ "\nWestern Division Selected"))
			((= Div "E_") (princ "\nEastern Division Selected"))
			((= Div "N_") (princ "\nNorthern Division Selected"))
			((= Div "SE") (princ "\nSouth-Eastern Division Selected"))
	)
	(if (and (findfile DivINI) (not DevMark))
		(foreach	DivNam
				Div_Lst
				(if	(=	(substr	(setq	TmpVal	(dos_getini	(StpDot AppNam)
															(strcat (car DivNam) ".DIVISION")
															DivINI
												)
								)
								1
								1
						)
						"*"
					)
					(dos_setini (StpDot AppNam) (strcat (car DivNam) ".DIVISION") (substr TmpVal 2) DivINI)
				)
				(if (= (car DivNam) Ch)
					(if (= (substr TmpVal 1 1) "*")
						(dos_setini (StpDot AppNam) (strcat (car DivNam) ".DIVISION") TmpVal DivINI)
						(dos_setini (StpDot AppNam) (strcat (car DivNam) ".DIVISION") (strcat "*" TmpVal) DivINI)
					)
				)
		)
	)
	(Bld_T_Fdr)
	(if Bug (princ "Done with DivSet!"))
	(princ)
)

(defun DivGet ( /	Bubba Cnt InData Hdr x Fn F0	; Initial Call to INI file to find chosen Division
				F1 Dsc DivINI Div_Lst DivNam TmpVal )
	(if Bug (princ "\n{DivGet entered\n"))
	(setq	DivINI		(strcat _Path-Person "DIV_MAP.INI")
			Cnt			0
			Div			nil
			Div_Lst		(list "BH" "S_" "W_" "E_" "M_" "SE" "AL" "GA")
	)
	(if (findfile DivINI)
		(foreach	DivNam
				Div_Lst
				(if (setq TmpVal (dos_getini (StpDot AppNam) (strcat DivNam ".DIVISION") DivINI))
					(if	(= (substr TmpVal 1 1) "*")
						(setq	Div		DivNam
								Div_Lst	(RepLst Div_Lst (cons DivNam (substr TmpVal 2)) Cnt)
						)
						(setq	Div_Lst	(RepLst Div_Lst (cons DivNam TmpVal) Cnt))
					)
				)
				(setq	Cnt	(1+ Cnt))
		)
		(princ "\nDiv_Map.INI file not found!")
	)
	(if Div
		(progn
			(setq	_Path-Div		(cdr (assoc Div Div_Lst))
					_Path-Panel	_Path-Div
					Bubba		(setvar "USERS3" Div)
			)
			(cond	((= Div "AL") (princ "\nAlabama Control Center Selected"))
					((= Div "GA") (princ "\nGeorgia Control Center Selected"))
					((= Div "BH") (princ "\nBirmingham Division Selected"))
					((= Div "S_") (princ "\nSouthern Division Selected"))
					((= Div "W_") (princ "\nWestern Division Selected"))
					((= Div "E_") (princ "\nEastern Division Selected"))
					((= Div "N_") (princ "\nNorthern Division Selected"))
					((= Div "SE") (princ "\nSouth-Eastern Division Selected"))
			)
			(if Lst_Fd_C
				(Bld_T_Fdr)
			)
		)
		(progn
			(alert (strcat "***" AppNam " Error***\nNot a valid Division Default!"))
			(UpdDivINI nil)
		)
	)
	(if	(and	DevMark
			Div
			(or	(= (StpDot AppNam) "ADDS")
				(= (StpDot AppNam) "ADDSPLOT")
				(= (StpDot AppNam) "BEMS")
				(wcmatch (StpDot AppNam) "CADET##")
				(= (StpDot AppNam) "SUBTOOLS")
				(wcmatch (StpDot AppNam) "ADDS##")
			)
		)
		(DivDevGet Div)
	)
	(if Bug (princ "\nDivGet exited}\n"))
	(princ)
)

(defun DivDevGet ( TDiv /	Urggh )			; Initial Call to INI file to find chosen Division - Development
	(if Bug (progn (princ "\n{DivDevGet entered - Parameter: \n")(prin1 TDiv)))
	(if (not (member (StpDot AppNam) (list "ADDS" "CADET" "ADDSPLOT")))
		(setq	_Path-Quad	(strcat TestPrmRootPath "Quad\\")
				_Path-DLG		(strcat TestPrmRootPath "Quad\\")
		)
		(setq	_Path-Quad	_Path-DLG)
	)
	(if AppNam
		(cond
			((= (StpDot AppNam) "ADDS")
				(setq    Urggh		"ADDS"
				)
			)
			((= (StpDot AppNam) "ADDS")
				(setq	_Path-Lisp	(strcat TestPrmRootPath "ADDS\\Lisp\\")
						Urggh		"ADDS"
				)
			)
			((= (StpDot AppNam) "ADDSPLOT")
				(setq	Urggh		"ADDSPLOT"
				)
			)
			((= (StpDot AppNam) "CADET")
				(setq    Urggh		"CADET"
				)
			)
			((wcmatch (StpDot AppNam) "CADET##")
				(setq	_Path-Lisp	(strcat TestPrmRootPath "Cadet20\\Lisp\\")
						_Path-LUT		(strcat TestPrmRootPath "LookUpTable\\")
						Urggh		"CADET2"
				)
			)
			((= (StpDot AppNam) "SUBTOOLS")
				(setq	_Path-Lisp	(strcat TestPrmRootPath "\SubTools\\Lisp\\")
						Urggh		"SUBTOOLS"
				)
			)
			((wcmatch (StpDot AppNam) "ADDS##")
				(setq	_Path-Lisp	(strcat TestPrmRootPath "Adds30\\Lisp\\")
						Urggh		"ADDS"
				)
			)
			(T
				(setq	_Path-Lisp	(strcat TestPrmRootPath "ADDS\\Lisp\\")
						Urggh		"ADDS"
				)
				(if Bug (princ "\n[Bug] Urggh set by default!"))
			)
		)
	)
	(if (and Bug Urggh) (princ (strcat "\n[Bug] Urggh:{" Urggh "}\n")))
	(cond
		((= TDiv "BH")
			(setq	_Path-Dwg		(strcat TestPrmRootPath "DivData\\Birmingham\\" Urggh "\\Dwg\\")
					Div			"BH"
			)
			(cond
			  	((= Urggh "ADDS")
					(setq	_Path-Div		(strcat TestPrmRootPath "DivData\\Birmingham\\ADDS\\Panel\\")
							_Path-Plot	(strcat TestPrmRootPath "Adds\\Plot\\")
							_Path-Panel	(strcat TestPrmRootPath "DivData\\Birmingham\\ADDS\\Panel\\")
							_M_Path-Panel	(strcat TestPrmRootPath "DivData\\Birmingham\\ADDS\\Panel\\")
							_N_Path-Panel  (strcat TestPrmRootPath "DivData\\Birmingham\\ADDS\\Panel\\")
							_M_AltP-Panel 	""
							_M_AltS-Panel	""
					)
				)
				((= Urggh "ADDSPLOT")
					(setq	_Path-Div		(strcat TestPrmRootPath "DivData\\Birmingham\\ADDS\\Panel\\")
							_Path-Plot	(strcat TestPrmRootPath "ADDS\\Plot\\")
							;	Comment the next line to use path from ini file for reading Adds Panels 
;							_Path-Panel	"S:\\Workgroups\\APC Birmingham Division\\Division Mapping Test\\DivData\\Birmingham\\Adds\\Panel\\"
					)
				)
				((= Urggh "SUBTOOLS")
					(setq	_Path-Div		(strcat TestPrmRootPath "DivData\\Birmingham\\ADDS\\Panel\\")
							_Path-Plot	(strcat TestPrmRootPath "ADDS\\Plot\\")
							_Path-User	(strcat TestPrmRootPath "ADDS\\User\\")
							_Path-Panel	(strcat TestPrmRootPath "DivData\\Birmingham\\SubTools\\Dwg\\")
							_Path-Dwg		(strcat TestPrmRootPath "DivData\\Birmingham\\" Urggh "\\Dwg\\")	;"C:\\MapQry\\Sub_BH\\"
							_Path-Dwf		(strcat TestPrmRootPath "DivData\\Birmingham\\" Urggh "\\Dwf\\")
					)
				)
			)
		)
		((= TDiv "E_")
			(setq	_Path-Dwf		(strcat TestPrmRootPath "DivData\\Eastern\\" Urggh "\\Dwf\\")
					_Path-Dwg		(strcat TestPrmRootPath "DivData\\Eastern\\" Urggh "\\Dwg\\")
					Div			"E_"
			)
			(cond
			  	((= Urggh "ADDS")
					(setq	_Path-Div		(strcat TestPrmRootPath "\DivData\\Eastern\\ADDS\\Panel\\")
							_Path-Plot	(strcat TestPrmRootPath "Adds\\Plot\\")
							_Path-Panel	(strcat TestPrmRootPath "DivData\\Eastern\\ADDS\\Panel\\")
							_M_Path-Panel	(strcat TestPrmRootPath "DivData\\Eastern\\ADDS\\Panel\\")
							_N_Path-Panel  (strcat TestPrmRootPath "DivData\\Eastern\\ADDS\\Panel\\")
							_M_AltP-Panel 	""
							_M_AltS-Panel	""
					)
				)
				((= Urggh "ADDSPLOT")
					(setq	_Path-Div		(strcat TestPrmRootPath "DivData\\Eastern\\ADDS\\Panel\\")
							_Path-Plot	(strcat TestPrmRootPath "ADDS\\Plot\\")
							;	Comment the next line to use path from ini file for reading Adds Panels 
;							_Path-Panel	"S:\\Workgroups\\APC Birmingham Division\\Division Mapping Test\\DivData\\Eastern\\Adds\\Panel\\"
					)
				)
				((= Urggh "SUBTOOLS")
					(setq	_Path-Div		(strcat TestPrmRootPath "DivData\\Eastern\\ADDS\\Panel\\")
							_Path-Plot	(strcat TestPrmRootPath "ADDS\\Plot\\")
							_Path-User	(strcat TestPrmRootPath "ADDS\\User\\")
							_Path-Panel	(strcat TestPrmRootPath "DivData\\Eastern\\SubTools\\Dwg\\")
							_Path-Dwg		(strcat TestPrmRootPath "DivData\\Eastern\\" Urggh "\\Dwg\\")	;"C:\\MapQry\\Sub_BH\\"
							_Path-Dwf		(strcat TestPrmRootPath "DivData\\Eastern\\" Urggh "\\Dwf\\")
					)
				)
			)
		)
		((= TDiv "M_")
			(setq	_Path-Dwf		(strcat TestPrmRootPath "DivData\\Mobile\\" Urggh "\\Dwf\\")
					_Path-Dwg		(strcat TestPrmRootPath "DivData\\Mobile\\" Urggh "\\Dwg\\")
					Div			"M_"
			)
			(cond
			  	((= Urggh "ADDS")
					(setq	_Path-Div		(strcat TestPrmRootPath "DivData\\Mobile\\ADDS\\Panel\\")
							_Path-Plot	(strcat TestPrmRootPath "Adds\\Plot\\")
							_Path-Panel	(strcat TestPrmRootPath "DivData\\Mobile\\ADDS\\Panel\\")
							M_Path-Panel	(strcat TestPrmRootPath "DivData\\Mobile\\ADDS\\Panel\\")
							_N_Path-Panel  (strcat TestPrmRootPath "DivData\\Mobile\\ADDS\\Panel\\")
							_M_AltP-Panel 	""
							_M_AltS-Panel	""

					)
				)
				((= Urggh "ADDSPLOT")
					(setq	_Path-Div		(strcat TestPrmRootPath "DivData\\Mobile\\ADDS\\Panel\\")
							_Path-Plot	(strcat TestPrmRootPath "ADDS\\Plot\\")
							;	Comment the next line to use path from ini file for reading Adds Panels 
;							_Path-Panel	"S:\\Workgroups\\APC Birmingham Division\\Division Mapping Test\\DivData\\Mobile\\Adds\\Panel\\"
					)
				)
				((= Urggh "SUBTOOLS")
					(setq	_Path-Div		(strcat TestPrmRootPath "DivData\\Mobile\\ADDS\\Panel\\")
							_Path-Plot	(strcat TestPrmRootPath "ADDS\\Plot\\")
							_Path-User	(strcat TestPrmRootPath "ADDS\\User\\")
							_Path-Panel	(strcat TestPrmRootPath "DivData\\Mobile\\SubTools\\Dwg\\")
							_Path-Dwg		(strcat TestPrmRootPath "DivData\\Mobile\\" Urggh "\\Dwg\\")	;"C:\\MapQry\\Sub_BH\\"
							_Path-Dwf		(strcat TestPrmRootPath "DivData\\Mobile\\" Urggh "\\Dwf\\")
					)
				)
			)
		)
		((= TDiv "S_")
			(setq	_Path-Dwf		(strcat TestPrmRootPath "DivData\\Southern\\" Urggh "\\Dwf\\")
					_Path-Dwg		(strcat TestPrmRootPath "DivData\\Southern\\" Urggh "\\Dwg\\")
					Div			"S_"
			)
			(cond
			  	((= Urggh "ADDS")
					(setq	_Path-Div		(strcat TestPrmRootPath "DivData\\Southern\\ADDS\\Panel\\")
							_Path-Plot	(strcat TestPrmRootPath "Adds\\Plot\\")
							_Path-Panel	(strcat TestPrmRootPath "DivData\\Southern\\ADDS\\Panel\\")
							_M_Path-Panel	(strcat TestPrmRootPath "DivData\\Southern\\ADDS\\Panel\\")
							_N_Path-Panel  (strcat TestPrmRootPath "DivData\\Southern\\ADDS\\Panel\\")
							_M_AltP-Panel 	""
							_M_AltS-Panel	""
					)
				)
				((= Urggh "ADDSPLOT")
					(setq	_Path-Div		(strcat TestPrmRootPath "DivData\\Southern\\ADDS\\Panel\\")
							_Path-Plot	(strcat TestPrmRootPath "ADDS\\Plot\\")
							;	Comment the next line to use path from ini file for reading Adds Panels 
;							_Path-Panel	"S:\\Workgroups\\APC Birmingham Division\\Division Mapping Test\\DivData\\Southern\\Adds\\Panel\\"
					)
				)
				((= Urggh "SUBTOOLS")
					(setq	_Path-Div		(strcat TestPrmRootPath "DivData\\Southern\\ADDS\\Panel\\")
							_Path-Plot	(strcat TestPrmRootPath "ADDS\\Plot\\")
							_Path-User	(strcat TestPrmRootPath "ADDS\\User\\")
							_Path-Panel	(strcat TestPrmRootPath "DivData\\Southern\\SubTools\\Dwg\\")
							_Path-Dwg		(strcat TestPrmRootPath "DivData\\Southern\\" Urggh "\\Dwg\\")	;"C:\\MapQry\\Sub_BH\\"
							_Path-Dwf		(strcat TestPrmRootPath "DivData\\Southern\\" Urggh "\\Dwf\\")
					)
				)
			)
		)
		((= TDiv "SE")
			(setq	_Path-Dwf		(strcat TestPrmRootPath "DivData\\SouthEast\\" Urggh "\\Dwf\\")
					_Path-Dwg		(strcat TestPrmRootPath "DivData\\SouthEast\\" Urggh "\\Dwg\\")
					Div			"SE"
			)
			(cond
			  	((= Urggh "ADDS")
					(setq	_Path-Div		(strcat TestPrmRootPath "DivData\\SouthEast\\ADDS\\Panel\\")
							_Path-Plot	(strcat TestPrmRootPath "Adds\\Plot\\")
							_Path-Panel	(strcat TestPrmRootPath "DivData\\SouthEast\\ADDS\\Panel\\")
							_M_Path-Panel	(strcat TestPrmRootPath "DivData\\SouthEast\\ADDS\\Panel\\")
							_N_Path-Panel  (strcat TestPrmRootPath "DivData\\SouthEast\\ADDS\\Panel\\")
							_M_AltP-Panel 	""
							_M_AltS-Panel	""
					)
				)
				((= Urggh "ADDSPLOT")
					(setq	_Path-Div		(strcat TestPrmRootPath "DivData\\SouthEast\\ADDS\\Panel\\")
							_Path-Plot	(strcat TestPrmRootPath "ADDS\\Plot\\")
							;	Comment the next line to use path from ini file for reading Adds Panels 
;							_Path-Panel	"S:\\Workgroups\\APC Birmingham Division\\Division Mapping Test\\DivData\\SouthEast\\Adds\\Panel\\"
					)
				)
				((= Urggh "SUBTOOLS")
					(setq	_Path-Div		(strcat TestPrmRootPath "DivData\\SouthEast\\ADDS\\Panel\\")
							_Path-Plot	(strcat TestPrmRootPath "ADDS\\Plot\\")
							_Path-User	(strcat TestPrmRootPath "ADDS\\User\\")
							_Path-Panel	(strcat TestPrmRootPath "DivData\\SouthEast\\SubTools\\Dwg\\")
							_Path-Dwg		(strcat TestPrmRootPath "DivData\\SouthEast\\" Urggh "\\Dwg\\")	;"C:\\MapQry\\Sub_BH\\"
							_Path-Dwf		(strcat TestPrmRootPath "DivData\\SouthEast\\" Urggh "\\Dwf\\")
					)
				)
			)
		)
		((= TDiv "W_")
			(setq	_Path-Dwf		(strcat TestPrmRootPath "DivData\\Western\\" Urggh "\\Dwf\\")
					_Path-Dwg		(strcat TestPrmRootPath "DivData\\Western\\" Urggh "\\Dwg\\")
					Div			"W_"
			)
			(cond
			  	((= Urggh "ADDS")
					(setq	_Path-Div		(strcat TestPrmRootPath "DivData\\Western\\ADDS\\Panel\\")
							_Path-Plot	(strcat TestPrmRootPath "Adds\\Plot\\")
							_Path-Panel	(strcat TestPrmRootPath "DivData\\Western\\ADDS\\Panel\\")
							_M_Path-Panel	(strcat TestPrmRootPath "DivData\\Western\\ADDS\\Panel\\")
							_N_Path-Panel  (strcat TestPrmRootPath "DivData\\Western\\ADDS\\Panel\\")
							_M_AltP-Panel 	""
							_M_AltS-Panel	""
					)
				)
				((= Urggh "ADDSPLOT")
					(setq	_Path-Div		(strcat TestPrmRootPath "DivData\\Western\\ADDS\\Panel\\")
							_Path-Plot	(strcat TestPrmRootPath "ADDS\\Plot\\")
							;	Comment the next line to use path from ini file for reading Adds Panels 
;							_Path-Panel	"S:\\Workgroups\\APC Birmingham Division\\Division Mapping Test\\DivData\\Western\\Adds\\Panel\\"
					)
				)
				((= Urggh "SUBTOOLS")
					(setq	_Path-Div		(strcat TestPrmRootPath "DivData\\Western\\ADDS\\Panel\\")
							_Path-Plot	(strcat TestPrmRootPath "ADDS\\Plot\\")
							_Path-User	(strcat TestPrmRootPath "ADDS\\User\\")
							_Path-Panel	(strcat TestPrmRootPath "DivData\\Western\\SubTools\\Dwg\\")
							_Path-Dwg		(strcat TestPrmRootPath "DivData\\Western\\" Urggh "\\Dwg\\") 
							_Path-Dwf		(strcat TestPrmRootPath "DivData\\Western\\" Urggh "\\Dwf\\")
					)
				)
			)
		)
		((= TDiv "AL")
			(setq	_Path-Dwf		(strcat TestPrmRootPath "\\" Urggh "\\Dwf\\")
					_Path-Dwg		(strcat TestPrmRootPath "\\" Urggh "\\Dwg\\")
					Div			"AL"
			)
			(cond			 ;	
			  	((= Urggh "ADDS")	;	Pointing to Production for ACC Windows 7 version of ADDS
					(setq	_Path-Div		 (strcat TestPrmRootPath "DivData\\ACC\\ADDS\\Panel\\")
							_Path-Plot	 (strcat TestPrmRootPath "DivData\\ACC\\Adds\\Plot\\")
							_Path-Panel	 (strcat TestPrmRootPath "DivData\\ACC\\ADDS\\Panel\\")			;(strcat TestPrmRootPath "ADDS\\Panel\\")
							_AltSPath-Panel (strcat TestPrmRootPath "DivData\\ACC\\SubTools\\Dwg\\")
							_M_Path-Panel	 (strcat TestPrmRootPath "DivData\\ACC\\ADDS\\Panel\\")
							_M_AltS-Panel   (strcat TestPrmRootPath "DivData\\ACC\\SubTools\\Dwg\\")
							_M_AltP-Panel	 (strcat TestPrmRootPath "DivData\\ACC\\SubTools\\Dwg\\")
							_N_Path-Panel   (strcat TestSecRootPath "DivData\\ACC\\ADDS\\Panel\\")
							_N_AltS-Panel	 (strcat TestPrmRootPath "DivData\\ACC\\SubTools\\Dwg\\")
							_N_AltP-Panel	 (strcat TestPrmRootPath "DivData\\ACC\\SubTools\\Dwg\\") 			; Was an empty string before.
					)
				)
			)
		)
		((= TDiv "GA")
			(setq	_Path-Dwf		(strcat TestPrmRootPath "DivData\\GCC\\" Urggh "\\Dwf\\")
					_Path-Dwg		(strcat TestPrmRootPath "DivData\\GCC\\" Urggh "\\Dwg\\")
					Div			"GA"
			)
			(cond
			  	((= Urggh "ADDS")
					(setq	_Path-Div		 (strcat TestPrmRootPath "DivData\\GCC\\ADDS\\Panel\\")
							_Path-Plot	 (strcat TestPrmRootPath "DivData\\GCC\\Adds\\Plot\\")
							_Path-Panel	 (strcat TestPrmRootPath "DivData\\GCC\\ADDS\\Panel\\")
							_M_Path-Panel	 (strcat TestPrmRootPath "DivData\\GCC\\ADDS\\Panel\\")
							_N_Path-Panel   (strcat TestPrmRootPath "DivData\\GCC\\ADDS\\Panel\\")
							_AltSPath-Panel (strcat TestPrmRootPath "DivData\\GCC\\SubTools\\Dwg\\")
							_M_AltS-Panel   (strcat TestPrmRootPath "DivData\\GCC\\SubTools\\Dwg\\")
							_N_AltS-Panel	 (strcat TestPrmRootPath "DivData\\GCC\\SubTools\\Dwg\\")
							_M_AltP-Panel 	""							
					)
				)
			)
		)
		(T
			(setq	_Path-Dwf		(strcat TestPrmRootPath "Public\\Birmingham\\" Urggh "\\Dwf\\")
					_Path-Dwg		(strcat TestPrmRootPath "DivData\\Birmingham\\" Urggh "\\Dwg\\")
					Div			"BH"
			)
			(cond
			  	((= Urggh "ADDS")
					(setq	_Path-Div		(strcat TestPrmRootPath "DivData\\Birmingham\\ADDS\\Panel\\")
							_Path-Plot	(strcat TestPrmRootPath "Adds\\Plot\\")
							_Path-Panel	(strcat TestPrmRootPath "Birmingham\\ADDS\\Panel\\")
					)
				)
				((= Urggh "ADDSPLOT")
					(setq	_Path-Div		(strcat TestPrmRootPath "DivData\\Birmingham\\ADDS\\Panel\\")
							_Path-Plot	(strcat TestPrmRootPath "ADDS\\Plot\\")
							;	Comment the next line to use path from ini file for reading Adds Panels 
							_Path-Panel	(strcat TestPrmRootPath "DivData\\Birmingham\\Adds\\Panel\\")
					)
				)
				((= Urggh "SUBTOOLS")
					(setq	_Path-Div		(strcat TestPrmRootPath "DivData\\Birmingham\\ADDS\\Panel\\")
							_Path-Plot	(strcat TestPrmRootPath "ADDS\\Plot\\")
							_Path-User	(strcat TestPrmRootPath "ADDS\\User\\")
							_Path-Panel	(strcat TestPrmRootPath "DivData\\Birmingham\\SubTools\\Dwg\\")
							_Path-Dwg		(strcat TestPrmRootPath "DivData\\Birmingham\\" Urggh "\\Dwg\\")	;"C:\\MapQry\\Sub_BH\\"
							_Path-Dwf		(strcat TestPrmRootPath "DivData\\Birmingham\\" Urggh "\\Dwf\\")
					)
				)
			)
		)
	)
	(if Bug (princ "\nDivDevGet exited}\n"))
)

(defun UpdDivINI ( Def	/	Bubba Cnt InData	; Updates INI file paths to Divisions
						Hdr x Fn F0 F1 Dsc DivINI
						Div_Lst TDiv Div_Pth TmpDiv )
	(if PanLst
		(if (/= (AddsQuit 2) 2)
			(setq	Bubba	(alert "You can't change Divisions with Panels open, you know.")
					Bubba	(exit)
			)
		)
	)
	(setq	DivINI	(strcat _Path-Person "DIV_MAP.INI")
			Div_Lst	(list	"BH" "S_" "W_" "E_" "M_" "SE" "AL" "GA")
			TDiv		nil
			Div_Pth	(list	nil nil nil nil nil nil nil nil)
	)
	(if (findfile DivINI)
		(progn
			(if (setq TmpDiv (dos_getini (StpDot AppNam) (strcat "BH" ".DIVISION") DivINI))
				(if (= (substr TmpDiv 1 1) "*")
					(setq	Div_Pth	(RepLst Div_Pth (cons "BH" (substr TmpDiv 2)) 0)
							TDiv		0
					)
					(setq	Div_Pth	(RepLst Div_Pth (cons "BH" TmpDiv) 0))
				)
				(setq	Div_Pth	(RepLst Div_Pth (cons "BH" "") 0))
			)
			(if (setq TmpDiv (dos_getini (StpDot AppNam) (strcat "S_" ".DIVISION") DivINI))
				(if (= (substr TmpDiv 1 1) "*")
					(setq	Div_Pth	(RepLst Div_Pth (cons "S_" (substr TmpDiv 2)) 1)
							TDiv		1
					)
					(setq	Div_Pth	(RepLst Div_Pth (cons "S_" TmpDiv) 1))
				)
				(setq	Div_Pth	(RepLst Div_Pth (cons "S_" "") 1))
			)
			(if (setq TmpDiv (dos_getini (StpDot AppNam) (strcat "W_" ".DIVISION") DivINI))
				(if (= (substr TmpDiv 1 1) "*")
					(setq	Div_Pth	(RepLst Div_Pth (cons "W_" (substr TmpDiv 2)) 2)
							TDiv		2
					)
					(setq	Div_Pth	(RepLst Div_Pth (cons "W_" TmpDiv) 2))
				)
				(setq	Div_Pth	(RepLst Div_Pth (cons "W_" "") 2))
			)
			(if (setq TmpDiv (dos_getini (StpDot AppNam) (strcat "E_" ".DIVISION") DivINI))
				(if (= (substr TmpDiv 1 1) "*")
					(setq	Div_Pth	(RepLst Div_Pth (cons "E_" (substr TmpDiv 2)) 3)
							TDiv		3
					)
					(setq	Div_Pth	(RepLst Div_Pth (cons "E_" TmpDiv) 3))
				)
				(setq	Div_Pth	(RepLst Div_Pth (cons "E_" "") 3))
			)
			(if (setq TmpDiv (dos_getini (StpDot AppNam) (strcat "M_" ".DIVISION") DivINI))
				(if (= (substr TmpDiv 1 1) "*")
					(setq	Div_Pth	(RepLst Div_Pth (cons "M_" (substr TmpDiv 2)) 4)
							TDiv		4
					)
					(setq	Div_Pth	(RepLst Div_Pth (cons "M_" TmpDiv) 4))
				)
				(setq	Div_Pth	(RepLst Div_Pth (cons "M_" "") 4))
			)
			(if (setq TmpDiv (dos_getini (StpDot AppNam) (strcat "SE" ".DIVISION") DivINI))
				(if (= (substr TmpDiv 1 1) "*")
					(setq	Div_Pth	(RepLst Div_Pth (cons "SE" (substr TmpDiv 2)) 5)
							TDiv		5
					)
					(setq	Div_Pth	(RepLst Div_Pth (cons "SE" TmpDiv) 5))
				)
				(setq	Div_Pth	(RepLst Div_Pth (cons "SE" "") 5))
			)
			
			(if (setq TmpDiv (dos_getini (StpDot AppNam) (strcat "AL" ".DIVISION") DivINI))
				(if (= (substr TmpDiv 1 1) "*")
					(setq	Div_Pth	(RepLst Div_Pth (cons "AL" (substr TmpDiv 2)) 6)
							TDiv		5
					)
					(setq	Div_Pth	(RepLst Div_Pth (cons "AL" TmpDiv) 6))
				)
				(setq	Div_Pth	(RepLst Div_Pth (cons "AL" "") 6))
			)
			(if (setq TmpDiv (dos_getini (StpDot AppNam) (strcat "GA" ".DIVISION") DivINI))
				(if (= (substr TmpDiv 1 1) "*")
					(setq	Div_Pth	(RepLst Div_Pth (cons "GA" (substr TmpDiv 2)) 7)
							TDiv		5
					)
					(setq	Div_Pth	(RepLst Div_Pth (cons "GA" TmpDiv) 7))
				)
				(setq	Div_Pth	(RepLst Div_Pth (cons "GA" "") 7))
			)
			
			(setq	Dlg	2)
		)
	)
	(if Def
		(if (member (strcase Def) Div_Lst)
			(setq	Div	(strcase Def)
					dlg	1
					XPanel 	(if (= Div "AL") 
								60000
								6000
							)
					YPanel 	(if (= Div "AL") 
								40000
								4000
							)
			)
;;;			(setq	Div	nil)
			(if (setq Dcl_Pan (findfile "Get_Init.dcl"))
				(if (> (setq Dcl_Pan (load_dialog Dcl_Pan)) 0)
					(while (> dlg 1)
						(new_dialog "DivPath" Dcl_Pan)
						(set_tile "Pth0" (cdr (nth 0 Div_Pth)))
						(set_tile "Pth1" (cdr (nth 1 Div_Pth)))
						(set_tile "Pth2" (cdr (nth 2 Div_Pth)))
						(set_tile "Pth3" (cdr (nth 3 Div_Pth)))
						(set_tile "Pth4" (cdr (nth 4 Div_Pth)))
						(set_tile "Pth5" (cdr (nth 5 Div_Pth)))
						(set_tile "Pth6" (cdr (nth 6 Div_Pth)))
						(set_tile "Pth7" (cdr (nth 7 Div_Pth)))
						(cond	((= Div "BH")
									(set_tile "Ch0" "1")
									(setq TDiv (Cb_Ch Div_Pth "1" 0))
								)
								((= Div "S_")
									(set_tile "Ch1" "1")
									(setq TDiv (Cb_Ch Div_Pth "1" 1))
								)
								((= Div "W_")
									(set_tile "Ch2" "1")
									(setq TDiv (Cb_Ch Div_Pth "1" 2))
								)
								((= Div "E_")
									(set_tile "Ch3" "1")
									(setq TDiv (Cb_Ch Div_Pth "1" 3))
								)
								((= Div "M_")
									(set_tile "Ch4" "1")
									(setq TDiv (Cb_Ch Div_Pth "1" 4))
								)
								((= Div "SE")
									(set_tile "Ch5" "1")
									(setq TDiv (Cb_Ch Div_Pth "1" 5))
								)
								
								((= Div "AL")
									(set_tile "Ch6" "1")
									(setq TDiv (Cb_Ch Div_Pth "1" 6))
								)
								((= Div "GA")
									(set_tile "Ch7" "1")
									(setq TDiv (Cb_Ch Div_Pth "1" 7))
								)
						)
						(action_tile "Pth0" "(setq Div_Pth (Cb_Pth Div_Pth $value 0))")
						(action_tile "Pth1" "(setq Div_Pth (Cb_Pth Div_Pth $value 1))")
						(action_tile "Pth2" "(setq Div_Pth (Cb_Pth Div_Pth $value 2))")
						(action_tile "Pth3" "(setq Div_Pth (Cb_Pth Div_Pth $value 3))")
						(action_tile "Pth4" "(setq Div_Pth (Cb_Pth Div_Pth $value 4))")
						(action_tile "Pth5" "(setq Div_Pth (Cb_Pth Div_Pth $value 5))")
						(action_tile "Pth6" "(setq Div_Pth (Cb_Pth Div_Pth $value 6))")
						(action_tile "Pth7" "(setq Div_Pth (Cb_Pth Div_Pth $value 7))")
						(action_tile "Ch0" "(setq TDiv (Cb_Ch Div_Pth $value 0))")
						(action_tile "Ch1" "(setq TDiv (Cb_Ch Div_Pth $value 1))")
						(action_tile "Ch2" "(setq TDiv (Cb_Ch Div_Pth $value 2))")
						(action_tile "Ch3" "(setq TDiv (Cb_Ch Div_Pth $value 3))")
						(action_tile "Ch4" "(setq TDiv (Cb_Ch Div_Pth $value 4))")
						(action_tile "Ch5" "(setq TDiv (Cb_Ch Div_Pth $value 5))")
						
						(action_tile "Ch6" "(setq TDiv (Cb_Ch Div_Pth $value 6))")
						(action_tile "Ch7" "(setq TDiv (Cb_Ch Div_Pth $value 7))")
						
						(action_tile "ok_button" "(done_dialog 1)")
						(setq dlg (start_dialog))
						(unload_dialog Dcl_Pan)
					)
					(alert "\nUnable to open DCL file")
				)
				(alert "\nUnable to find DCL file")
			)
		)
	)
	(if (and (= dlg 1) (not DevMark))
;	(if (= dlg 1)
		(progn
			(if (findfile DivINI)
				(progn
					(if (> (strlen (cdr (nth 0 Div_Pth))) 1)
						(if (= Div "BH")
							(dos_setini (StpDot AppNam) (strcat "BH" ".DIVISION") (strcat "*" (cdr (nth 0 Div_Pth))) DivINI)
							(dos_setini (StpDot AppNam) (strcat "BH" ".DIVISION") (cdr (nth 0 Div_Pth)) DivINI)
						)
					)
					(if (> (strlen (cdr (nth 1 Div_Pth))) 1)
						(if (= Div "S_")
							(dos_setini (StpDot AppNam) (strcat "S_" ".DIVISION") (strcat "*" (cdr (nth 1 Div_Pth))) DivINI)
							(dos_setini (StpDot AppNam) (strcat "S_" ".DIVISION") (cdr (nth 1 Div_Pth)) DivINI)
						)
					)
					(if (> (strlen (cdr (nth 2 Div_Pth))) 1)
						(if (= Div "W_")
							(dos_setini (StpDot AppNam) (strcat "W_" ".DIVISION") (strcat "*" (cdr (nth 2 Div_Pth))) DivINI)
							(dos_setini (StpDot AppNam) (strcat "W_" ".DIVISION") (cdr (nth 2 Div_Pth)) DivINI)
						)
					)
					(if (> (strlen (cdr (nth 3 Div_Pth))) 1)
						(if (= Div "E_")
							(dos_setini (StpDot AppNam) (strcat "E_" ".DIVISION") (strcat "*" (cdr (nth 3 Div_Pth))) DivINI)
							(dos_setini (StpDot AppNam) (strcat "E_" ".DIVISION") (cdr (nth 3 Div_Pth)) DivINI)
						)
					)
					(if (> (strlen (cdr (nth 4 Div_Pth))) 1)
						(if (= Div "M_")
							(dos_setini (StpDot AppNam) (strcat "M_" ".DIVISION") (strcat "*" (cdr (nth 4 Div_Pth))) DivINI)
							(dos_setini (StpDot AppNam) (strcat "M_" ".DIVISION") (cdr (nth 4 Div_Pth)) DivINI)
						)
					)
					(if (> (strlen (cdr (nth 5 Div_Pth))) 1)
						(if (= Div "SE")
							(dos_setini (StpDot AppNam) (strcat "SE" ".DIVISION") (strcat "*" (cdr (nth 5 Div_Pth))) DivINI)
							(dos_setini (StpDot AppNam) (strcat "SE" ".DIVISION") (cdr (nth 5 Div_Pth)) DivINI)
						)
					)
					
					(if (> (strlen (cdr (nth 5 Div_Pth))) 1)
						(if (= Div "AL")
							(dos_setini (StpDot AppNam) (strcat "AL" ".DIVISION") (strcat "*" (cdr (nth 6 Div_Pth))) DivINI)
							(dos_setini (StpDot AppNam) (strcat "AL" ".DIVISION") (cdr (nth 6 Div_Pth)) DivINI)
						)
					)
					(if (> (strlen (cdr (nth 5 Div_Pth))) 1)
						(if (= Div "GA")
							(dos_setini (StpDot AppNam) (strcat "GA" ".DIVISION") (strcat "*" (cdr (nth 7 Div_Pth))) DivINI)
							(dos_setini (StpDot AppNam) (strcat "GA" ".DIVISION") (cdr (nth 7 Div_Pth)) DivINI)
						)
					)
				)
			)
			(if Div
				(progn
					(setq	_Path-Div		(cdr (assoc Div Div_Pth))
							_PATH-PANEL	_Path-Div
							Bubba		(setvar "USERS3" Div)
					)
					(cond	((= Div "BH") (princ "\nBirmingham Division Selected"))
							((= Div "S_") (princ "\nSouthern Division Selected"))
							((= Div "W_") (princ "\nWestern Division Selected"))
							((= Div "E_") (princ "\nEastern Division Selected"))
							((= Div "N_") (princ "\nNorthern Division Selected"))
							((= Div "SE") (princ "\nSouth-Eastern Division Selected"))
							
							((= Div "AL") (princ "\nTransmission - Alabama Control Center Selected"))
							((= Div "GA") (princ "\nTransmission - Georgia Control Center Selected"))
			
					)
					(if (= (strcase (substr _Path-Panel 1 1)) "S")
						(UpdPanPth _Path-Panel)
					)
					(if Lst_Fd_XY
						(setq	Lst_Fd_XY		nil)
					)
					(if Lst_Sb_XY
						(setq	Lst_Sb_XY		nil)
					)
					(if Lst_Fd_Nam
						(setq	Lst_Fd_Nam	nil)
					)
					(if Lst_Sb_Nam
						(setq	Lst_Sb_Nam	nil)
					)
					(Bld_T_Fdr)
				)
			)
			(princ "\nDiv Paths/Choice Updated!")
		)
		(if DevMark
			(progn
				(setq	Bubba		(setvar "USERS3" Div))
				(princ "\nPt1 Division :")(prin1 Div)
				(DivDevGet Div)
				(cond	((= Div "BH") (princ "\nBirmingham Division Selected"))
						((= Div "S_") (princ "\nSouthern Division Selected"))
						((= Div "W_") (princ "\nWestern Division Selected"))
						((= Div "E_") (princ "\nEastern Division Selected"))
						((= Div "N_") (princ "\nNorthern Division Selected"))
						((= Div "SE") (princ "\nSouth-Eastern Division Selected"))
						
						((= Div "AL") (princ "\nTransmission - Alabama Control Center Selected"))
						((= Div "GA") (princ "\nTransmission - Georgia Control Center Selected"))
				)
				(princ "\nDivision :")(prin1 Div)
				(if (= (strcase (substr _Path-Panel 1 1)) "S")
					(UpdPanPth _Path-Panel)
				)
				(if Lst_Fd_XY
					(setq	Lst_Fd_XY		nil)
				)
				(if Lst_Sb_XY
					(setq	Lst_Sb_XY		nil)
				)
				(if Lst_Fd_Nam
					(setq	Lst_Fd_Nam	nil)
				)
				(if Lst_Sb_Nam
					(setq	Lst_Sb_Nam	nil)
				)
				(Bld_T_Fdr)
				(princ "\nDiv Update not written to INI file\nChanges made\n")
			)
			(alert "Div Update Cancelled\nChanges not made")
		)
	)
	(if _M_Path-Panel
		(if (AND (/= Div "AL") (/= Div "GA"))
			(progn
				(DivGetUnix Div)
			)
		)
	)
	(princ)
)

(defun UpdPanPth ( NewPath /	StubPath Fnam IsIt ); Validates & updates division dependent paths
	(if _Path-Person
		(setq	Fnam		(strcat _Path-Person "DIV_MAP.INI"))
		(setq	Fnam		(Find_INI))
	)
	(if NewPath
		(cond
		  	((= (StpDot AppNam) "ADDS")
				(setq	StubPath	(substr NewPath 1 (- (strlen NewPath) 6)))
			)
		  	((= (StpDot AppNam) "ADDS")
				(setq	StubPath	(substr NewPath 1 (- (strlen NewPath) 6)))
			)
		  	((= (StpDot AppNam) "ADDSPLOT")
				(setq	StubPath	(substr NewPath 1 (- (strlen NewPath) 6)))
			)
			((= (StpDot AppNam) "CADET")
				(setq	StubPath	NewPath)
			)
		  	((= (StpDot AppNam) "SUBTOOLS")
				(setq	StubPath	(substr NewPath 1 (- (strlen NewPath) 4)))
			)
		)
		(setq	StubPath	nil)
	)
	(if (and Bug StubPath)
		(princ (strcat "\nBug:StubPath=>" StubPath "<"))
	)
	(if StubPath
		(setq	IsIt		(TstPth (dos_splitpath StubPath)))
		(setq	IsIt		nil)
	)
	(if (and Bug IsIt)
		(princ (strcat "\nBug:IsIt=>Good<"))
	)
	(if (and IsIt (not DevMark))
;	(if IsIt 
		(progn
			(if (= (StpDot AppNam) "CADET")
				(if (TstPth (dos_splitpath StubPath))
					(setq	_Path-Dwg		StubPath
							Bubba		(dos_setini (StpDot AppNam) "Dwg" _Path-Dwg Fnam)
							Bubba		(if Bug (princ "\nUpdating Drawing Path!"))
					)
					(alert (strcat "***" AppNam " Error***\nDrawing Path Not Updated with Division Change!"))
				)
				(if (TstPth (dos_splitpath (strcat StubPath "DWG\\")))
					(setq	_Path-Dwg		(strcat StubPath "DWG\\")
							Bubba		(dos_setini (StpDot AppNam) "Dwg" _Path-Dwg Fnam)
							Bubba		(if Bug (princ "\nUpdating Drawing Path!"))
					)
					(alert (strcat "***" AppNam " Error***\nDrawing Path Not Updated with Division Change!"))
				)
			)
			(if (and 	(TstPth (dos_splitpath (strcat StubPath "DWF\\")))
					(member (StpDot AppNam) (list "ADDS" "ADDS" "ADDSPLOT" "SUBTOOLS")))
				(setq	_Path-DWF		(strcat StubPath "DWF\\")
						Bubba		(dos_setini (StpDot AppNam) "DWF" _Path-DWF Fnam)
						Bubba		(if Bug (princ "\nUpdating DWF Path!"))
				)
				(if (member (StpDot AppNam) (list "ADDS" "ADDS" "ADDSPLOT" "SUBTOOLS"))
					(alert (strcat "***" AppNam " Error***\nDWF Path Not Updated with Division Change!"))
				)
			)
			(if (and (TstPth (dos_splitpath (strcat StubPath "PLOT\\"))) (member (StpDot AppNam) (list "ADDS" "ADDS" "ADDSPLOT")))
				(setq	_Path-Plot	(strcat StubPath "PLOT\\")
						Bubba		(dos_setini (StpDot AppNam) "Plot" _Path-Plot Fnam)
						Bubba		(if Bug (princ "\nUpdating Plot Path!"))
				)
;;;				(if (member (StpDot AppNam) (list "ADDS" "ADDS" "ADDSPLOT"))
;;;					(alert (strcat "***" AppNam " Error***\nPlot Path Not Updated with Division Change!"))
;;;				)
			)
		)
		(if Isit
			(progn
				(if (TstPth (dos_splitpath (strcat StubPath "DWG\\")))
					(setq	_Path-Dwg		(strcat StubPath "DWG\\")
							Bubba		(if Bug (princ "\nUpdating Drawing Path!"))
					)
					(alert (strcat "***" AppNam " Error***\nDrawing Path Not Updated with Division Change!"))
				)
				(if (TstPth (dos_splitpath (strcat StubPath "DWF\\")))
					(setq	_Path-DWF		(strcat StubPath "DWF\\")
							Bubba		(if Bug (princ "\nUpdating DWF Path!"))
					)
					(alert (strcat "***" AppNam " Error***\nDWF Path Not Updated with Division Change!"))
				)
				(if (and (TstPth (dos_splitpath (strcat StubPath "PLOT\\"))) (member (StpDot AppNam) (list "ADDS" "ADDS" "ADDSPLOT")))
					(setq	_Path-Plot	(strcat StubPath "PLOT\\")
							Bubba		(if Bug (princ "\nUpdating Plot Path!"))
					)
				)
			)
		)
	)
	(princ)
)

(defun Cb_Pth ( Div_Pth PVal PPos / Tstr TVal )	; Call Back function to test paths of Divisions
	(setq	Tstr		(list nil "" " " "  " "   " "    " "     "))
	(if (not (member PVal Tstr))
		(if (TstPth (dos_splitpath PVal))
			(setq	TVal		(strcase PVal))
			(setq	TVal		" ")
		)
		(setq	TVal	" ")
	)
	(setq	Div_Pth	(RepLst Div_Pth (cons (car (nth PPos Div_Pth)) TVal) PPos))
	(cond	((= PPos 0) (set_tile "Pth0" (strcase TVal)))
			((= PPos 1) (set_tile "Pth1" (strcase TVal)))
			((= PPos 2) (set_tile "Pth2" (strcase TVal)))
			((= PPos 3) (set_tile "Pth3" (strcase TVal)))
			((= PPos 4) (set_tile "Pth4" (strcase TVal)))
			((= PPos 5) (set_tile "Pth5" (strcase TVal)))
	)
	(cond	((= (get_tile "Ch0") "1") (setq TPos 0))
			((= (get_tile "Ch1") "1") (setq TPos 1))
			((= (get_tile "Ch2") "1") (setq TPos 2))
			((= (get_tile "Ch3") "1") (setq TPos 3))
			((= (get_tile "Ch4") "1") (setq TPos 4))
			((= (get_tile "Ch5") "1") (setq TPos 5))
			(T (setq TPos 6))
	)
	(if	(and	(or	(member (get_tile "Pth0") Tstr) (> (strlen (cdr (nth 0 Div_Pth))) 1))
			(or	(member (get_tile "Pth1") Tstr) (> (strlen (cdr (nth 1 Div_Pth))) 1))
			(or	(member (get_tile "Pth2") Tstr) (> (strlen (cdr (nth 2 Div_Pth))) 1))
			(or	(member (get_tile "Pth3") Tstr) (> (strlen (cdr (nth 3 Div_Pth))) 1))
			(or	(member (get_tile "Pth4") Tstr) (> (strlen (cdr (nth 4 Div_Pth))) 1))
			(or	(member (get_tile "Pth5") Tstr) (> (strlen (cdr (nth 5 Div_Pth))) 1))
			(and (>= TPos 0) (<= TPos 5))
		)
		(mode_tile "ok_button" 0)
		(mode_tile "ok_button" 1)
	)
	Div_Pth
)

(defun Cb_Ch ( Div_Pth PVal PPos / TPos Tstr )	; Call Back function to test Division Choice
	(setq	Tstr		(list nil "" " " "  " "   " "    " "     " "      " "       "))
	(cond	((and (= PPos 0) (> (strlen (get_tile "Pth0")) 4))
				(setq	Div	"BH")
				(set_tile "Ch0" "1")
				(set_tile "Ch1" "0")
				(set_tile "Ch2" "0")
				(set_tile "Ch3" "0")
				(set_tile "Ch4" "0")
				(set_tile "Ch5" "0")
				(set_tile "Ch6" "0")
				(set_tile "Ch7" "0")
			)
			((and (= PPos 1) (> (strlen (get_tile "Pth1")) 4))
				(setq	Div	"S_")
				(set_tile "Ch0" "0")
				(set_tile "Ch1" "1")
				(set_tile "Ch2" "0")
				(set_tile "Ch3" "0")
				(set_tile "Ch4" "0")
				(set_tile "Ch5" "0")
				(set_tile "Ch6" "0")
				(set_tile "Ch7" "0")
			)
			((and (= PPos 2) (> (strlen (get_tile "Pth2")) 4))
				(setq	Div	"W_")
				(set_tile "Ch0" "0")
				(set_tile "Ch1" "0")
				(set_tile "Ch2" "1")
				(set_tile "Ch3" "0")
				(set_tile "Ch4" "0")
				(set_tile "Ch5" "0")
				(set_tile "Ch6" "0")
				(set_tile "Ch7" "0")
			)
			((and (= PPos 3) (> (strlen (get_tile "Pth3")) 4))
				(setq	Div	"E_")
				(set_tile "Ch0" "0")
				(set_tile "Ch1" "0")
				(set_tile "Ch2" "0")
				(set_tile "Ch3" "1")
				(set_tile "Ch4" "0")
				(set_tile "Ch5" "0")
				(set_tile "Ch6" "0")
				(set_tile "Ch7" "0")
			)
			((and (= PPos 4) (> (strlen (get_tile "Pth4")) 4))
				(setq	Div	"M_")
				(set_tile "Ch0" "0")
				(set_tile "Ch1" "0")
				(set_tile "Ch2" "0")
				(set_tile "Ch3" "0")
				(set_tile "Ch4" "1")
				(set_tile "Ch5" "0")
				(set_tile "Ch6" "0")
				(set_tile "Ch7" "0")
			)
			((and (= PPos 5) (> (strlen (get_tile "Pth5")) 4))
				(setq	Div	"SE")
				(set_tile "Ch0" "0")
				(set_tile "Ch1" "0")
				(set_tile "Ch2" "0")
				(set_tile "Ch3" "0")
				(set_tile "Ch4" "0")
				(set_tile "Ch5" "1")
				(set_tile "Ch6" "0")
				(set_tile "Ch7" "0")
			)
			((and (= PPos 6) (> (strlen (get_tile "Pth6")) 4))
				(setq	Div	"AL")
				(set_tile "Ch0" "0")
				(set_tile "Ch1" "0")
				(set_tile "Ch2" "0")
				(set_tile "Ch3" "0")
				(set_tile "Ch4" "0")
				(set_tile "Ch5" "0")
				(set_tile "Ch6" "1")
				(set_tile "Ch7" "0")
			)
			((and (= PPos 6) (> (strlen (get_tile "Pth7")) 4))
				(setq	Div	"GA")
				(set_tile "Ch0" "0")
				(set_tile "Ch1" "0")
				(set_tile "Ch2" "0")
				(set_tile "Ch3" "0")
				(set_tile "Ch4" "0")
				(set_tile "Ch5" "0")
				(set_tile "Ch6" "0")
				(set_tile "Ch7" "1")
			)
			(T
				(set_tile "Ch0" "0")
				(set_tile "Ch1" "0")
				(set_tile "Ch2" "0")
				(set_tile "Ch3" "0")
				(set_tile "Ch4" "0")
				(set_tile "Ch5" "0")
			)
	)
	(setq	TPos		PPos)
	(if	(and	(or	(member (get_tile "Pth0") Tstr) (> (strlen (cdr (nth 0 Div_Pth))) 1))
			(or	(member (get_tile "Pth1") Tstr) (> (strlen (cdr (nth 1 Div_Pth))) 1))
			(or	(member (get_tile "Pth2") Tstr) (> (strlen (cdr (nth 2 Div_Pth))) 1))
			(or	(member (get_tile "Pth3") Tstr) (> (strlen (cdr (nth 3 Div_Pth))) 1))
			(or	(member (get_tile "Pth4") Tstr) (> (strlen (cdr (nth 4 Div_Pth))) 1))
			(or	(member (get_tile "Pth5") Tstr) (> (strlen (cdr (nth 5 Div_Pth))) 1))
			(or	(member (get_tile "Pth6") Tstr) (> (strlen (cdr (nth 6 Div_Pth))) 1))
			(or	(member (get_tile "Pth7") Tstr) (> (strlen (cdr (nth 7 Div_Pth))) 1))
			(and (>= TPos 0) (<= TPos 7))
		)
		(mode_tile "ok_button" 0)
		(mode_tile "ok_button" 1)
	)
	(nth PPos (list "BH" "S_" "W_" "E_" "M_" "SE" "AL" "GA"))
)

(defun ResetSPick01 (	Fnam /	MySndPick		; Re-creates PickBox keys in Acad14.cfg
							ChzInt CurPick )
	(if Bug (princ "\n{ResetSPick01 Entered"))
	(if SndPick01
		(setq	CurPick	SndPick01
				ChzInt	-3
		)
		(setq	CurPick	10
				ChzInt	-3
		)
	)
	(initget 1 "View")
	(if (null MyLst)
		(RWav nil)
	)
	(if (and MyLst Fnam)
		(while (or (< ChzInt -1) (> ChzInt (length MyLst)) (= ChzInt "View"))
			(setq	ChzInt	(getint (strcat "\nWhat would you like to set your StartUp Sound file to? (<V>iew list, <-1> for No Sound or sound number [" (itoa (1+ CurPick)) "]): ")))
			(if (= ChzInt "View")
				(textscr)
			)
			(if (= ChzInt "View")
				(terpri)
			)
			(if (= ChzInt "View")
				(princ	(strcat	"\n"
								(PadCharR (itoa -1) 3)
								(PadCharR	"No Sound" 16)
								"No Sound at all"
						)
				)
			)
			(if (= ChzInt "View")
				(princ	(strcat	"\n"
								(PadCharR (itoa 0) 3)
								(PadCharR	"Random" 16)
								"Any sound on the list from 11-37"
						)
				)
			)
			(if (= ChzInt "View")
				(foreach	WavOne
						MyLst
						(princ	(strcat	"\n"
										(PadCharR (itoa (1+ (nth 1 WavOne))) 3)
										(PadCharR	(nth 0 WavOne) 16)
										(nth 2 WavOne)
								)
						)
				)
			)
			(if (= ChzInt "View")
				(setq	ChzInt	-3)
				(if (or (< ChzInt -1) (> ChzInt (length MyLst)))
					(setq	Bubba	(princ "\nYour value was invalid... try again.\n")
							ChzInt	-3
					)
				)
			)
			(if (and (>= ChzInt -1) (<= ChzInt (length MyLst)))
				(progn
					(if (not (= (dos_getini (StpDot AppNam) "SndPick01Test" Fnam) "1"))
						(dos_setini (StpDot AppNam) "SndPick01Test" "1" Fnam)
					)
					(dos_setini (StpDot AppNam) "SndPick01Val" (itoa (1- ChzInt)) Fnam)
					(setq	SndPick01		(1- ChzInt))
					(cond
						((and (> ChzInt 0) (<= ChzInt (length MyLst)))
							(princ (strcat "\nIt's sound number: <" (itoa ChzInt) ">, and it sounds like this:"))
						)
						((= ChzInt 0)
							(princ (strcat "\nIt's the Random Sound number: <" (itoa ChzInt) ">, and it can sound like this:"))
						)
						((= ChzInt -1)
							(princ (strcat "\nIt's the No Sound number: <" (itoa ChzInt) ">, and it sounds like this: <grin>"))
						)
						((< ChzInt -1)
							(princ (strcat "\nIt's the Say What? Sound number: <" (itoa ChzInt) ">, and it sounds like this: <grin>"))
						)
					)
					
					(RWav SndPick01)
					(princ)
				)
			)
		)
	)
	(if Bug (princ "\nResetSPick01 Exited}\n"))
	(princ)
)

(defun ResetSPick02 (	Fnam /	MySndPick		; Re-creates PickBox keys in Acad14.cfg
							ChzInt CurPick )
	(if Bug (princ "\n{ResetSPick02 Entered"))
	(if SndPick02
		(setq	CurPick	SndPick02
				ChzInt	-3
		)
		(setq	CurPick	10
				ChzInt	-3
		)
	)
	(if (null MyLst)
		(RWav nil)
	)
	(initget 1 "View")
	(if (and MyLst Fnam)
		(while (or (< ChzInt -1) (> ChzInt (length MyLst)) (= ChzInt "View"))
			(setq	ChzInt	(getint (strcat "\nWhat would you like to set your Error Sound file to? (<V>iew list, <-1> for No Sound or sound number [" (itoa (1+ CurPick)) "]): ")))
			(if (= ChzInt "View")
				(textscr)
			)
			(if (= ChzInt "View")
				(terpri)
			)
			(if (= ChzInt "View")
				(princ	(strcat	"\n"
								(PadCharR (itoa -1) 3)
								(PadCharR	"No Sound" 16)
								"No Sound at all"
						)
				)
			)
			(if (= ChzInt "View")
				(princ	(strcat	"\n"
								(PadCharR (itoa 0) 3)
								(PadCharR	"Random" 16)
								"Any sound on the list from 11-37"
						)
				)
			)
			(if (= ChzInt "View")
				(foreach	WavOne
						MyLst
						(princ	(strcat	"\n"
										(PadCharR (itoa (1+ (nth 1 WavOne))) 3)
										(PadCharR	(nth 0 WavOne) 16)
										(nth 2 WavOne)
								)
						)
				)
			)
			(if (= ChzInt "View")
				(setq	ChzInt	-3)
				(if (or (< ChzInt -1) (> ChzInt (length MyLst)))
					(setq	Bubba	(princ "\nYour value was invalid... try again.\n")
							ChzInt	-3
					)
				)
			)
			(if (and (>= ChzInt -1) (<= ChzInt (length MyLst)))
				(progn
					(if (not (= (dos_getini (StpDot AppNam) "SndPick02Test" Fnam) "1"))
						(dos_setini (StpDot AppNam) "SndPick02Test" "1" Fnam)
					)
					(dos_setini (StpDot AppNam) "SndPick02Val" (itoa (1- ChzInt)) Fnam)
					(setq	SndPick02		(1- ChzInt))
					(cond
						((and (> ChzInt 0) (<= ChzInt (length MyLst)))
							(princ (strcat "\nIt's sound number: <" (itoa ChzInt) ">, and it sounds like this:"))
						)
						((= ChzInt 0)
							(princ (strcat "\nIt's the Random Sound number: <" (itoa ChzInt) ">, and it can sound like this:"))
						)
						((= ChzInt -1)
							(princ (strcat "\nIt's the No Sound number: <" (itoa ChzInt) ">, and it sounds like this: <grin>"))
						)
						((< ChzInt -1)
							(princ (strcat "\nIt's the Say What? Sound number: <" (itoa ChzInt) ">, and it sounds like this: <grin>"))
						)
					)
					
					(RWav SndPick02)
					(princ)
				)
			)
		)
	)
	(if Bug (princ "\nResetSPick02 Exited}\n"))
	(princ)
)

(defun DivGetUnix ( Div / )						; Initial Call to build paths for chosen Division
	(if DevMark
		(setq	_Alt_Path-Panel	(strcat TestPrmRootPath "Shared Panels\\"))
		(setq	_Alt_Path-Panel	(strcat PrmRootPath "Shared Panels\\"))
	)
	(cond
		((= Div "BH")
			(cond
				((wcmatch (strcase (substr AppNam 1 4)) "ADDS")
					(setq	_M_Path-Panel		(strcat AltPrmRootDwg "Birmingham\\Adds\\Panel\\")
							_M_AltP-Panel		(strcat AltPrmRootDwg "Shared Panels\\")
							_M_AltS-Panel		(strcat AltPrmRootDwg "Birmingham\\SubTools\\Dwg\\")
							_N_Path-Panel		(strcat AltSecRootDwg "Birmingham\\Adds\\Panel\\")
							_N_AltP-Panel		(strcat AltSecRootDwg "Shared Panels")
							_N_AltS-Panel		(strcat AltSecRootDwg "Birmingham\\SubTools\\Dwg\\")
;							_AltSPath-Panel	(strcat TestPrmRootPath "DivData\\Birmingham\\SubTools\\Dwg\\")			; [TODO] ask Ed if this is correct
							_AltSPath-Panel	"S:\\Workgroups\\APC Birmingham Division\\Division Mapping\\SubTools\\Dwg\\"
					)
				)
				
				((wcmatch (strcase (substr AppNam 1 4)) "SUBT")
					(setq	_M_Path-Panel	(strcat AltPrmRootDwg "Birmingham\\SubTools\\Dwg\\")
							_N_Path-Panel	(strcat AltSecRootDwg "Birmingham\\SubTools\\Dwg\\")
					)
				)
				(T
					(alert (strcat "***" AppNam " Error***\nCould not validate Application setting for paths"))
					(exit)
				)
			)
		)
		((= Div "E_")
			(cond
				((wcmatch (strcase (substr AppNam 1 4)) "ADDS")
					(setq	_M_Path-Panel		(strcat AltPrmRootDwg "Eastern\\Adds\\Panel\\")
							_M_AltP-Panel		(strcat AltPrmRootDwg "Shared Panels\\")
							_M_AltS-Panel		(strcat AltPrmRootDwg "Eastern\\SubTools\\Dwg\\")
							_N_Path-Panel		(strcat AltSecRootDwg "Eastern\\Adds\\Panel\\")
							_N_AltP-Panel		(strcat AltSecRootDwg "Shared Panels\\")
							_N_AltS-Panel		(strcat AltSecRootDwg "Eastern\\SubTools\\Dwg\\")
;							_AltSPath-Panel	(strcat TestPrmRootPath "DivData\\Eastern\\SubTools\\Dwg\\")
							_AltSPath-Panel	"S:\\Workgroups\\APC Eastern Division\\Division Mapping\\SubTools\\Dwg\\"
					)
				)
				
				((wcmatch (strcase (substr AppNam 1 4)) "SUBT")
					(setq	_M_Path-Panel	(strcat AltPrmRootDwg "Eastern\\SubTools\\Dwg\\")
							_N_Path-Panel	(strcat AltSecRootDwg "Eastern\\SubTools\\Dwg\\")
					)
				)
				(T
					(alert (strcat "***" AppNam " Error***\nCould not validate Application setting for paths"))
					(exit)
				)
			)
		)
		((= Div "M_")
			(cond
				((wcmatch (strcase (substr AppNam 1 4)) "ADDS")
					(setq	_M_Path-Panel		(strcat AltPrmRootDwg "Mobile\\Adds\\Panel\\")
							_M_AltP-Panel		(strcat AltPrmRootDwg "Shared Panels\\")
							_M_AltS-Panel		(strcat AltPrmRootDwg "Mobile\\SubTools\\Dwg\\")
							_N_Path-Panel		(strcat AltSecRootDwg "Mobile\\Adds\\Panel\\")
							_N_AltP-Panel		(strcat AltSecRootDwg "Shared Panels\\")
							_N_AltS-Panel		(strcat AltSecRootDwg "Mobile\\SubTools\\Dwg\\")
;							_AltSPath-Panel	(strcat TestPrmRootPath "DivData\\Mobile\\SubTools\\Dwg\\")
							_AltSPath-Panel	"S:\\Workgroups\\APC Mobile Division\\Division Mapping\\SubTools\\Dwg\\"
					)
				)
				
				((wcmatch (strcase (substr AppNam 1 4)) "SUBT")
					(setq	_M_Path-Panel	(strcat AltPrmRootDwg "Mobile\\SubTools\\Dwg\\")
							_N_Path-Panel	(strcat AltSecRootDwg "Mobile\\SubTools\\Dwg\\")
					)
				)
				(T
					(alert (strcat "***" AppNam " Error***\nCould not validate Application setting for paths"))
					(exit)
				)
			)
		)
		((= Div "S_")
			(cond
				((wcmatch (strcase (substr AppNam 1 4)) "ADDS")
					(setq	_M_Path-Panel		(strcat AltPrmRootDwg "Southern\\Adds\\Panel\\")
							_M_AltP-Panel		(strcat AltPrmRootDwg "Shared Panels\\")
							_M_AltS-Panel		(strcat AltPrmRootDwg "Southern\\SubTools\\Dwg\\")
							_N_Path-Panel		(strcat AltSecRootDwg "Southern\\Adds\\Panel\\")
							_N_AltP-Panel		(strcat AltSecRootDwg "Shared Panels\\")
							_N_AltS-Panel		(strcat AltSecRootDwg "Southern\\SubTools\\Dwg\\")
;							_AltSPath-Panel	(strcat TestPrmRootPath "DivData\\Southern\\SubTools\\Dwg\\")
							_AltSPath-Panel	"S:\\Workgroups\\APC Southern Division\\Division Mapping\\SubTools\\Dwg\\"
					)
				)
				
				((wcmatch (strcase (substr AppNam 1 4)) "SUBT")
					(setq	_M_Path-Panel	(strcat AltPrmRootDwg "Southern\\SubTools\\Dwg\\")
							_N_Path-Panel	(strcat AltSecRootDwg "Southern\\SubTools\\Dwg\\")
					)
				)
				(T
					(alert (strcat "***" AppNam " Error***\nCould not validate Application setting for paths"))
					(exit)
				)
			)
		)
		((= Div "SE")
			(cond
				((wcmatch (strcase (substr AppNam 1 4)) "ADDS")
					(setq	_M_Path-Panel		(strcat AltPrmRootDwg "SouthEast\\Adds\\Panel\\")
							_M_AltP-Panel		(strcat AltPrmRootDwg "Shared Panels\\")
							_M_AltS-Panel		(strcat AltPrmRootDwg "SouthEast\\SubTools\\Dwg\\")
							_N_Path-Panel		(strcat AltSecRootDwg "SouthEast\\Adds\\Panel\\")
							_N_AltP-Panel		(strcat AltSecRootDwg "Shared Panels\\")
							_N_AltS-Panel		(strcat AltSecRootDwg "SouthEast\\SubTools\\Dwg\\")
;							_AltSPath-Panel	(strcat TestPrmRootPath "DivData\\SouthEast\\SubTools\\Dwg\\")
							_AltSPath-Panel	"S:\\Workgroups\\APC SouthEast Division\\Division Mapping\\SubTools\\Dwg\\"
					)
				)
				
				((wcmatch (strcase (substr AppNam 1 4)) "SUBT")
					(setq	_M_Path-Panel	(strcat AltPrmRootDwg "SouthEast\\SubTools\\Dwg\\")
							_N_Path-Panel	(strcat AltSecRootDwg "SouthEast\\SubTools\\Dwg\\")
					)
				)
				(T
					(alert (strcat "***" AppNam " Error***\nCould not validate Application setting for paths"))
					(exit)
				)
			)
		)
		((= Div "W_")
			(cond
				((wcmatch (strcase (substr AppNam 1 4)) "ADDS")
					(setq	_M_Path-Panel		(strcat AltPrmRootDwg "Western\\Adds\\Panel\\")
							_M_AltP-Panel		(strcat AltPrmRootDwg "Shared Panels\\")
							_M_AltS-Panel		(strcat AltPrmRootDwg "Western\\SubTools\\Dwg\\")
							_N_Path-Panel		(strcat AltSecRootDwg "Western\\Adds\\Panel\\")
							_N_AltP-Panel		(strcat AltSecRootDwg "Shared Panels\\")
							_N_AltS-Panel		(strcat AltSecRootDwg "Western\\SubTools\\Dwg\\")
;							_AltSPath-Panel	(strcat TestPrmRootPath "DivData\\Western\\SubTools\\Dwg\\")
							_AltSPath-Panel	"S:\\Workgroups\\APC Western Division\\Division Mapping\\SubTools\\Dwg\\"
					)
				)
				
				((wcmatch (strcase (substr AppNam 1 4)) "SUBT")
					(setq	_M_Path-Panel	(strcat AltPrmRootDwg "Western\\SubTools\\Dwg\\")
							_N_Path-Panel	(strcat AltSecRootDwg "SouthEast\\SubTools\\Dwg\\")
					)
				)
				(T
					(alert (strcat "***" AppNam " Error***\nCould not validate Application setting for paths"))
					(exit)
				)
			)
		)
		((= Div "AL")
			(cond
				((wcmatch (strcase (substr AppNam 1 4)) "ADDS")
					(setq	_M_Path-Panel	(strcat SecRootPath "DivData\\ACC\\ADDS\\Panel\\")
							_M_AltP-Panel  "" ;;(strcat SecRootPath "DivData\\ACC\\ADDS\\Panel\\") ;""
							_AltSPath-Panel	(strcat PrmRootPath "SubTools\\Dwg\\")
							_M_AltS-Panel  	(strcat AltPrmRootDwg "ACC\\SubTools\\Dwg\\")
							_N_AltS-Panel		(strcat AltPrmRootDwg "ACC\\SubTools\\Dwg\\")
							_N_Path-Panel	""
					)
				)
			)
		)
		((= Div "GA")
			(cond
				((wcmatch (strcase (substr AppNam 1 4)) "ADDS")
					(setq	_M_Path-Panel		(strcat SecRootPath "DivData\\GCC\\ADDS\\Panel\\")
							_M_AltP-Panel  	(strcat SecRootPath "DivData\\GCC\\ADDS\\Panel\\")		; [CET Test] Shared Panel
							_AltSPath-Panel	(strcat PrmRootPath "SubTools\\Dwg\\")
							_M_AltS-Panel  	(strcat AltPrmRootDwg "GCC\\SubTools\\Dwg\\")
							_N_AltS-Panel		(strcat AltPrmRootDwg "GCC\\SubTools\\Dwg\\")
							_N_Path-Panel	""													; - Geo Panel alt location
							_N_AltP-Panel		(strcat AltPrmRootDwg "DivData\\GCC\\ADDS\\Panel\\")		; [CET Test] Shared Panel
					)
				)
			)
		)
		(T
			(alert (strcat "***" AppNam " Error***\nCould not validate Division setting for paths"))
			(exit)
		)
	)
)

(defun DecodeDivisionPath ( / )
	(cond
		((= Div "BH")
			(setq divisionName "APC Birmingham Division")
		)
		((= Div "E_")
			(setq divisionName "APC Eastern Division")
		)
		((= Div "M_")
			(setq divisionName "APC Mobile Division")
		)
		((= Div "S_")
			(setq divisionName "APC Southern Division")
		)
		((= Div "SE")
			(setq divisionName "APC Southeast Division")
		)
		((= Div "W_")
			(setq divisionName "APC Western Division")
		)
		((= Div "AL")
			(setq divisionName "APC Power Delivery-ACC")		; [CET] - trying to add transmission to this function.
		)
		((= Div "GA")
			(setq divisionName "GPC Real-Time Systems")		; [CET] - trying to add transmission to this function.
		)
	)
)

(defun DecodeTargetPathDwf ( Detail / basePath decodeDetail divisionName)
	(if Bug (princ (strcat "\nDecodeTargetPathDwf - Entered\n   parameters passed in Detail = " Detail "\n")))
	(if DevMark 
		(setq basePath (strcat TestPrmRootPath "Public\\"))
		(setq basePath (strcat PrmRootPath "Public\\"))
	)
	(cond
		((= Div "BH")
			(setq divisionName "Birmingham\\")
		)
		((= Div "E_")
			(setq divisionName "Birmingham\\")
		)
		((= Div "M_")
			(setq divisionName "Mobile\\")
		)
		((= Div "S_")
			(setq divisionName "Montgomery\\")
		)
		((= Div "SE")
			(setq divisionName "Montgomery\\")
		)
		((= Div "W_")
			(setq divisionName "Tuscaloosa\\")
		)
	)
	(cond
		((= Detail "DIST AREA MAP")
			(setq decodeDetail "DistArea\\")
		)
		((= Detail "FEEDER AREA MAP")
			(setq decodeDetail "Feeder\\")
		)
		((= Detail "SUB AREA MAP")
			(setq decodeDetail "Sub_Area\\")
		)
		((= Detail "SUBSINGLE MAP")
			(setq decodeDetail "SubSingle\\")
		)
		(T
			(setq decodeDetail "Other\\")
		)
	)
 					
	(setq Result (strcat basePath divisionName decodeDetail))
	(if Bug (princ "\nDecodeTargetPathDwf - Done\n"))
	(princ Result)
)

(defun UpCdtPths ( / saveDiv Fnam chkPth iniPth)
	(if Bug (princ "\nGet_Init.lsp!UpCdtPths - Entered\n"))
	
	;	Gets current division and saves it for later restore.
	(if (null Div)
		(DivGet)		; gets selected division from INI file.
	)
	(setq saveDiv Div)
	
	;	Setup and check ini file for incorrect path and rewrite paths if need.
	(setq	Fnam	(Find_INI))	; get path to INI file.
	(setq 	chkPth 	"S:\\WorkGroups\\APC Birmingham Division\\Division Mapping\\Cadet\\"
			iniPth	(dos_getini "CADET" "BH.DIVISION" fnam)
	)
	(if (= (substr iniPth 1 1) "*")
		(setq iniPth (substr iniPth 2))
	)
	(if (/= chkPth iniPth)
		(progn
			(dos_setini "CADET" "BH.DIVISION" chkPth fnam)
			(dos_setini "CADET" "E_.DIVISION" "S:\\WorkGroups\\APC Eastern Division\\Division Mapping\\Cadet\\" fnam)
			(dos_setini "CADET" "M_.DIVISION" "S:\\WorkGroups\\APC Mobile Division\\Division Mapping\\Cadet\\" fnam)
			(dos_setini "CADET" "S_.DIVISION" "S:\\WorkGroups\\APC Southern Division\\Division Mapping\\Cadet\\" fnam)
			(dos_setini "CADET" "SE.DIVISION" "S:\\WorkGroups\\APC SouthEast Division\\Division Mapping\\Cadet\\" fnam)
			(dos_setini "CADET" "W_.DIVISION" "S:\\WorkGroups\\APC Western Division\\Division Mapping\\Cadet\\" fnam)
		)
	)
	
	;	Restore Division in INI file.
	(UpdDivINI saveDiv)
)


(setq	LodVer	"16.0")
